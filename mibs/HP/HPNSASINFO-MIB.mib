-- ****************************************************************************
-- HP NSA System Information MIB
-- September 28, 1997
--
-- Copyright Hewlett-Packard Company 1994-97.
-- All rights reserved.
--
-- The information in this document is subject to change without notice.
--
-- The HP enterprise number is 11. The ASN.1 prefix to, and including,
-- the HP enterprise ID is 1.3.6.1.4.1.11.
--
-- ****************************************************************************
-- Summary of HP NSA System Information MIB
-- ****************************************************************************
-- hp                                              (1.3.6.1.4.1.11)
--    nm                                           (hp.2)
--       hpnsa                                     (nm.23)
--          hpnsaSystemInfo Group                  (hpnsa.7)
--             hpnsaSiMibRev Group                 (hpnsa.7.1)
--                hpnsaSiMibRevMajor               (hpnsa.7.1.1)
--                hpnsaSiMibRevMinor               (hpnsa.7.1.2)
--             hpnsaSiAgent Group                  (hpnsa.7.2)
--                hpnsaSiAgentTable                (hpnsa.7.2.1)
--                   hpnsaSiAgentEntry             (hpnsa.7.2.1.1)
--                      hpnsaSiAgentIndex          (hpnsa.7.2.1.1.1)
--                      hpnsaSiAgentName           (hpnsa.7.2.1.1.2)
--                      hpnsaSiAgentVersion        (hpnsa.7.2.1.1.3)
--                      hpnsaSiAgentDate           (hpnsa.7.2.1.1.4)
--             hpnsaSiBasicInfo Group              (hpnsa.7.3)
--                hpnsaSiModel                     (hpnsa.7.3.1)
--                hpnsaSiBIOSVersion               (hpnsa.7.3.2)
--                hpnsaSiVideoBIOSVersion          (hpnsa.7.3.3)
--                hpnsaSiSCSIBIOSVersion           (hpnsa.7.3.4)
--                hpnsaSiNumEISASlots              (hpnsa.7.3.5)
--                hpnsaSiNumPCISlots               (hpnsa.7.3.6)
--                hpnsaSiNumCPU                    (hpnsa.7.3.7)
--                hpnsaSiCPUTable                  (hpnsa.7.3.8)
--                   hpnsaSiCPUEntry               (hpnsa.7.3.8.1)
--                      hpnsaSiCPUIndex            (hpnsa.7.3.8.1.1)
--                      hpnsaSiCPUModel            (hpnsa.7.3.8.1.2)
--                      hpnsaSiCPUSpeed            (hpnsa.7.3.8.1.3)
--                hpnsaSiOpSysType                 (hpnsa.7.3.9)
--                hpnsaSiOpSysVer                  (hpnsa.7.3.10)
--                hpnsaSiSystemName                (hpnsa.7.3.11)
--                hpnsaSiSystemID                  (hpnsa.7.3.12)
--                hpnsaSiKbdType                   (hpnsa.7.3.13)
--                hpnsaSiMouseType                 (hpnsa.7.3.14)
--                hpnsaSiVideoType                 (hpnsa.7.3.15)
--                hpnsaSiNumISASlots               (hpnsa.7.3.16)
--                hpnsaSiModelName                 (hpnsa.7.3.17)
--                hpnsaSiOpSysDescription          (hpnsa.7.3.18)
--             hpnsaSiSecurity Group               (hpnsa.7.4)
--                hpnsaSiPowerOnPassword           (hpnsa.7.4.1)
--                hpnsaSiNetServerMode             (hpnsa.7.4.2)
--                hpnsaSiKeyboardLockPassword      (hpnsa.7.4.3)
--                hpnsaSiVideoBlankMode            (hpnsa.7.4.4)
--                hpnsaSiBootDiskPriority          (hpnsa.7.4.5)
--                hpnsaSiWriteToFloppy             (hpnsa.7.4.6)
--                hpnsaSiKbdMouseInactivityTO      (hpnsa.7.4.7)
--             hpnsaSiPort Group                   (hpnsa.7.5)
--                hpnsaSiPortTable                 (hpnsa.7.5.1)
--                   hpnsaSiPortEntry              (hpnsa.7.5.1.1)
--                      hpnsaSiPortIndex           (hpnsa.7.5.1.1.1)
--                      hpnsaSiPortType            (hpnsa.7.5.1.1.2)
--                      hpnsaSiPortStartAddress    (hpnsa.7.5.1.1.3)
--                      hpnsaSiPortEndAddress      (hpnsa.7.5.1.1.4)
--                      hpnsaSiPortInterruptNum    (hpnsa.7.5.1.1.5)
--             hpnsaSiMemory Group                 (hpnsa.7.6)
--                hpnsaSiBaseMemSize               (hpnsa.7.6.1)
--                hpnsaSiExtMemSize                (hpnsa.7.6.2)
--                hpnsaSiMemType                   (hpnsa.7.6.3)
--                hpnsaSiMemSpeed                  (hpnsa.7.6.4)
--             hpnsaSiFloppyDrive Group            (hpnsa.7.8)
--                hpnsaSiNumFloppyDrives           (hpnsa.7.8.1)
--                hpnsaSiFloppyDriveTable          (hpnsa.7.8.2)
--                   hpnsaSiFloppyDriveEntry       (hpnsa.7.8.2.1)
--                      hpnsaSiFloppyDriveIndex    (hpnsa.7.8.2.1.1)
--                      hpnsaSiFloppyDriveType     (hpnsa.7.8.2.1.2)
--             hpnsaSiRemoteLocatorLED Group       (hpnsa.7.9)
--                hpnsaSiRemoteLocatorLEDSupported (hpnsa.7.9.1)
--                hpnsaSiRemoteLocatorLEDStatus    (hpnsa.7.9.2)
--                hpnsaSiRemoteLocatorLEDSet       (hpnsa.7.9.3)
--
-- ****************************************************************************
-- 
-- REVISION INFO:
--    1.0    Initial
--    1.1    Added SiNumISASlots
--    1.2    Added Build information to SiOpSysVer
--    1.3    Removed SiHardDisk
--    1.4    Added CPU_Pentium_II
--    1.5    Added hpnsaSiRemoteLocatorLED Group
--           Added hpnsaSiModelName to hpnsaSiBasicInfo Group
--           Added hpnsaSiOpSysDescription to hpnsaSiBasicInfo Group
--           MIB Revision Changed to 1.1


HPNSASINFO-MIB DEFINITIONS ::= BEGIN
   IMPORTS
      enterprises    FROM RFC1155-SMI
      DisplayString  FROM RFC1213-MIB
      OBJECT-TYPE    FROM RFC-1212;

   hp                      OBJECT IDENTIFIER ::= { enterprises 11 }
   nm                      OBJECT IDENTIFIER ::= { hp 2 }
   hpnsa                   OBJECT IDENTIFIER ::= { nm 23 }
   hpnsaSystemInfo         OBJECT IDENTIFIER ::= { hpnsa 7 }
   hpnsaSiMibRev           OBJECT IDENTIFIER ::= { hpnsaSystemInfo 1 }
   hpnsaSiAgent            OBJECT IDENTIFIER ::= { hpnsaSystemInfo 2 }
   hpnsaSiBasicInfo        OBJECT IDENTIFIER ::= { hpnsaSystemInfo 3 }
   hpnsaSiSecurity         OBJECT IDENTIFIER ::= { hpnsaSystemInfo 4 }
   hpnsaSiPort             OBJECT IDENTIFIER ::= { hpnsaSystemInfo 5 }
   hpnsaSiMemory           OBJECT IDENTIFIER ::= { hpnsaSystemInfo 6 }
   hpnsaSiFloppyDrive      OBJECT IDENTIFIER ::= { hpnsaSystemInfo 8 }
   hpnsaSiRemoteLocatorLED OBJECT IDENTIFIER ::= { hpnsaSystemInfo 9 }

-- ****************************************************************************
-- HP NSA System Information MIB Revision
-- ======================================
--
-- hp                                              (1.3.6.1.4.1.11)
--    nm                                           (hp.2)
--       hpnsa                                     (nm.23)
--          hpnsaSystemInfo Group                  (hpnsa.7)
--             hpnsaSiMibRev Group                 (hpnsa.7.1)
--                hpnsaSiMibRevMajor               (hpnsa.7.1.1)
--                hpnsaSiMibRevMinor               (hpnsa.7.1.2)
--
-- Implementation of the MibRev group is mandatory for all HPNSA Agents
-- supporting the HP NSA System Information MIB.
--
-- An HPNSA Agent conforming to this document will return a
-- hpnsaSiMibRevMajor of 1 and a hpnsaSiMibRevMinor of 1.
--
-- ****************************************************************************

   hpnsaSiMibRevMajor OBJECT-TYPE
      SYNTAX INTEGER (1..65535)
      ACCESS read-only
      STATUS mandatory
      DESCRIPTION
	 "The major revision level of the MIB."
   ::= { hpnsaSiMibRev 1 }

   hpnsaSiMibRevMinor OBJECT-TYPE
      SYNTAX INTEGER (0..65535)
      ACCESS read-only
      STATUS mandatory
      DESCRIPTION
	 "The minor revision level of the MIB."
   ::= { hpnsaSiMibRev 2 }

-- ****************************************************************************
-- HP NSA System Information Agent Information
-- ===========================================
--
-- hp                                              (1.3.6.1.4.1.11)
--    nm                                           (hp.2)
--       hpnsa                                     (nm.23)
--          hpnsaSystemInfo Group                  (hpnsa.7)
--             hpnsaSiAgent Group                  (hpnsa.7.2)
--                hpnsaSiAgentTable                (hpnsa.7.2.1)
--                   hpnsaSiAgentEntry             (hpnsa.7.2.1.1)
--                      hpnsaSiAgentIndex          (hpnsa.7.2.1.1.1)
--                      hpnsaSiAgentName           (hpnsa.7.2.1.1.2)
--                      hpnsaSiAgentVersion        (hpnsa.7.2.1.1.3)
--                      hpnsaSiAgentDate           (hpnsa.7.2.1.1.4)
--
--  Implementation of the hpnsaSiAgent group is mandatory for all
--  HPNSA Agents that support the System Information MIB.
--
-- ****************************************************************************
-- HP NSA System Information Agent Table
-- ****************************************************************************

   hpnsaSiAgentTable OBJECT-TYPE
      SYNTAX SEQUENCE OF HPnsaSiAgentEntry
      ACCESS not-accessible
      STATUS mandatory
      DESCRIPTION
	 "A table of software modules that provide an interface to the
	 device this MIB describes."
   ::= { hpnsaSiAgent 1 }

   hpnsaSiAgentEntry OBJECT-TYPE
      SYNTAX HPnsaSiAgentEntry
      ACCESS not-accessible
      STATUS mandatory
      DESCRIPTION
	 "A description of the Agents that access system information."
      INDEX { hpnsaSiAgentIndex }
   ::= { hpnsaSiAgentTable 1 }

   HPnsaSiAgentEntry ::= SEQUENCE {
      hpnsaSiAgentIndex       INTEGER,
      hpnsaSiAgentName        DisplayString,
      hpnsaSiAgentVersion     DisplayString,
      hpnsaSiAgentDate        OCTET STRING
   }

   hpnsaSiAgentIndex OBJECT-TYPE
      SYNTAX INTEGER (0..255)
      ACCESS read-only
      STATUS mandatory
      DESCRIPTION
	 "A unique index for this agent."
   ::= { hpnsaSiAgentEntry 1 }

   hpnsaSiAgentName OBJECT-TYPE
      SYNTAX DisplayString (SIZE (0..255))
      ACCESS read-only
      STATUS mandatory
      DESCRIPTION
	 "Name of the agent/agents satisfying SNMP requests for this MIB."
    ::= { hpnsaSiAgentEntry 2 }

   hpnsaSiAgentVersion OBJECT-TYPE
      SYNTAX DisplayString (SIZE (0..10))
      ACCESS read-only
      STATUS mandatory
      DESCRIPTION
	 "Version number of the agent/agents satisfying SNMP requests for
	 this MIB."
   ::= { hpnsaSiAgentEntry 3 }

   hpnsaSiAgentDate OBJECT-TYPE
      SYNTAX OCTET STRING (SIZE (7))
      ACCESS read-only
      STATUS mandatory
      DESCRIPTION
	 "The date on which this agent was created.

	 field  octets  contents                  range
	 _________________________________________________
	    1       1    years since 1900          0..255
	    2       2    month                     1..12
	    3       3    day                       1..31
	    4       4    hour                      0..23
	    5       5    minute                    0..59
	    6       6    second                    0..59"
   ::= { hpnsaSiAgentEntry 4 }

-- ****************************************************************************
-- HP NSA System Information Basic Info Group
-- ==========================================
--
-- hp                                              (1.3.6.1.4.1.11)
--    nm                                           (hp.2)
--       hpnsa                                     (nm.23)
--          hpnsaSystemInfo Group                  (hpnsa.7)
--             hpnsaSiBasicInfo Group              (hpnsa.7.3)
--                hpnsaSiModel                     (hpnsa.7.3.1)
--                hpnsaSiBIOSVersion               (hpnsa.7.3.2)
--                hpnsaSiVideoBIOSVersion          (hpnsa.7.3.3)
--                hpnsaSiSCSIBIOSVersion           (hpnsa.7.3.4)
--                hpnsaSiNumEISASlots              (hpnsa.7.3.5)
--                hpnsaSiNumPCISlots               (hpnsa.7.3.6)
--                hpnsaSiNumCPU                    (hpnsa.7.3.7)
--                hpnsaSiCPUTable                  (hpnsa.7.3.8)
--                   hpnsaSiCPUEntry               (hpnsa.7.3.8.1)
--                      hpnsaSiCPUIndex            (hpnsa.7.3.8.1.1)
--                      hpnsaSiCPUModel            (hpnsa.7.3.8.1.2)
--                      hpnsaSiCPUSpeed            (hpnsa.7.3.8.1.3)
--                hpnsaSiOpSysType                 (hpnsa.7.3.9)
--                hpnsaSiOpSysVer                  (hpnsa.7.3.10)
--                hpnsaSiSystemName                (hpnsa.7.3.11)
--                hpnsaSiSystemID                  (hpnsa.7.3.12)
--                hpnsaSiKbdType                   (hpnsa.7.3.13)
--                hpnsaSiMouseType                 (hpnsa.7.3.14)
--                hpnsaSiVideoType                 (hpnsa.7.3.15)
--                hpnsaSiNumISASlots               (hpnsa.7.3.16)
--                hpnsaSiModelName                 (hpnsa.7.3.17)
--                hpnsaSiOpSysDescription          (hpnsa.7.3.18)
--
-- The hpnsaSiSystemInfo group contains system specific information.
--
-- ****************************************************************************

   hpnsaSiModel OBJECT-TYPE
      SYNTAX INTEGER {
	HP_Vectra_PC            (0),
	HP_Vectra_ES_12_PC      (1), 
	HP_Vectra_RS_20_PC      (2),
	HP_Vectra_PortableCS_PC (3),
	HP_Vectra_ES_PC         (4),
	HP_Vectra_CS_PC         (5),
	HP_Vectra_RS_16_PC      (6), 
	HP_Vectra_QS_16_PC      (7), 
	HP_Vectra_QS_20_PC      (8), 
	HP_Vectra_RS_20C_PC     (9), 
	HP_Vectra_RS_25C_PC     (10), 
	HP_Vectra_LS_286_PC     (11), 
	HP_Vectra_QS_16S_PC     (12), 
	HP_Vectra_386_25_PC     (13), 
	HP_Vectra_486_25T_PC    (14), 
	HP_Vectra_286_12_PC     (15), 
	HP_Vectra_486_33T_PC    (16), 
	HP_Vectra_386_20_PC     (17), 
	HP_Vectra_386_16N_PC    (18), 
	HP_Vectra_386_20N_PC    (19), 
	HP_Vectra_486s_20_PC    (20), 
	HP_Vectra_386s_20_PC    (21), 
	HP_Vectra_486_25U_PC    (22), 
	HP_Vectra_486_33U_PC    (23), 
	HP_Vectra_486_50U_PC    (24), 
	HP_Vectra_486_66U_PC    (25), 
	HP_Vectra_486_ST_Series (26),
	HP_Vectra_386_25N       (27),
	HP_Vectra_486_N         (28),
	HP_Vectra_386s_25       (29),
	HP_Vectra_386_33N       (30),
	HP_Vectra_486_33N       (32),
	HP_NetServer_LE_Series  (35),
	HP_NetServer_LM_Series  (36),
	HP_NetServer_LF_Series  (40),
	HP_NetServer_LC_Series  (41),
	HP_NetServer_LS_Series  (42),
	HP_NetServer_LH_Series  (43),
	HP_NetServer_LC_Series  (44),
	HP_NetServer_LX_Series  (46),
	HP_NetServer_LH_Series  (47),
	HP_NetServer_LH_Series  (49),
	HP_NetServer_E_Series   (50),
	HP_NetServer_E_Series   (51),
	HP_NetServer_LD_Series  (52),
	HP_NetServer_Racks_Series(54),
	HP_NetServer_LC_Series  (55),
	HP_NetServer_E_Series   (56),
	HP_NetServer_LX_Series   (57),
	HP_NetServer_E_Series   (58),
	HP_NetServer_E_Series   (59),
	HP_NetServer_LH_Series  (60),
	HP_NetServer_LC_Series  (61),
	HP_NetServer_LH_Series  (62),
	HP_NetServer_LH_Series  (63),
	HP_NetServer_LX_Series  (64),
	HP_NetServer_LX_Series  (65),
	HP_NetServer_LH3000	(66),
	HP_NetServer_LH6000	(67),
	HP_NetServer_LC2000	(68),
	HP_NetServer_LT6000  	(69),
	HP_NetServer_E_Series   (70),
	HP_NetServer_E_Series  	(71),
        HP_NetServer_LP1000r    (72),
        HP_NetServer_LP2000r    (73),
        HP_NetServer_tc6100     (75),
        HP_NetServer_tc3100     (79),
        HP_NetServer_tc4100     (80),
        HP_NetServer_lh6000u3   (82),
        HP_NetServer_lt6000ru3  (83),
        HP_NetServer_lc2000u3   (84),
        HP_NetServer_lh3000u3   (85),
        HP_NetServer_lp1000r    (86),
        HP_NetServer_lp2000r    (87),
        HP_NetServer_tc7100     (88),
        HP_NetServer_rc7100     (89)
	
	
      }            
      ACCESS read-only
      STATUS mandatory
      DESCRIPTION
	 "System model"
   ::= { hpnsaSiBasicInfo 1 }

   hpnsaSiBIOSVersion OBJECT-TYPE
      SYNTAX DisplayString (SIZE (0..255))
      ACCESS read-only
      STATUS mandatory
      DESCRIPTION
	 "Version number of the system BIOS."
   ::= { hpnsaSiBasicInfo 2 }

   hpnsaSiVideoBIOSVersion OBJECT-TYPE
      SYNTAX DisplayString (SIZE (0..255))
      ACCESS read-only
      STATUS optional
      DESCRIPTION
	 "Version number of the video BIOS."
   ::= { hpnsaSiBasicInfo 3 }

   hpnsaSiSCSIBIOSVersion OBJECT-TYPE
      SYNTAX DisplayString (SIZE (0..255))
      ACCESS read-only
      STATUS mandatory
      DESCRIPTION
	 "Version number of the SCSI BIOS."
   ::= { hpnsaSiBasicInfo 4 }

   hpnsaSiNumEISASlots OBJECT-TYPE
      SYNTAX INTEGER
      ACCESS read-only
      STATUS mandatory
      DESCRIPTION
	 "Number of EISA slots in the system."
   ::= { hpnsaSiBasicInfo 5 }

   hpnsaSiNumPCISlots OBJECT-TYPE
      SYNTAX INTEGER
      ACCESS read-only
      STATUS mandatory
      DESCRIPTION
	 "Number of PCI slots in the system."
   ::= { hpnsaSiBasicInfo 6 }
   
   hpnsaSiNumCPU OBJECT-TYPE
      SYNTAX INTEGER
      ACCESS read-only
      STATUS mandatory
      DESCRIPTION
	 "Number of CPUs installed in the system."
   ::= { hpnsaSiBasicInfo 7 }

   hpnsaSiCPUTable OBJECT-TYPE
      SYNTAX SEQUENCE OF HPnsaSiCPUEntry
      ACCESS not-accessible
      STATUS mandatory
      DESCRIPTION
	 "A table of CPU types installed in the system."
   ::= { hpnsaSiBasicInfo 8 }

   hpnsaSiCPUEntry OBJECT-TYPE
      SYNTAX HPnsaSiCPUEntry
      ACCESS not-accessible
      STATUS mandatory
      DESCRIPTION
	 "A description of the CPUs installed in the system."
      INDEX { hpnsaSiCPUIndex }
   ::= { hpnsaSiCPUTable 1 }

   HPnsaSiCPUEntry ::= SEQUENCE {
      hpnsaSiCPUIndex   INTEGER,
      hpnsaSiCPUModel   INTEGER,
      hpnsaSiCPUSpeed   INTEGER
   }

   hpnsaSiCPUIndex OBJECT-TYPE
      SYNTAX INTEGER (0..255)
      ACCESS read-only
      STATUS mandatory
      DESCRIPTION
	 "A unique index for this CPU."
   ::= { hpnsaSiCPUEntry 1 }

   hpnsaSiCPUModel OBJECT-TYPE
      SYNTAX INTEGER {
	CPU_80286(0),
	CPU_8088(1),
	CPU_8086(2),
	CPU_80386(3),
	CPU_80386_SX(4),
	CPU_486_DX(5),
	CPU_486_SX(6),
	CPU_486_DX2_or_OverDrive(8),
	CPU_486_P23T(9),
	CPU_487_SX(10),
	CPU_Pentium(11),
	CPU_Pentium_OverDrive(12),
	CPU_486_24C(13),
	CPU_Pentium_Series_P54C(14),
	CPU_Pentium_Series_P54CT(15),
	CPU_Pentium_Series_P54CM(16),
	CPU_486_SX2(17),
	CPU_486_SL(18),
	CPU_Pentium_Series_P6(19),
	CPU_Pentium_II(20),
	CPU_Pentium_II_Xeon(21),
	CPU_Pentium_III(22),
	CPU_Pentium_III_Xeon(23),
	CPU_Itanium(25),
	notPresent(253),
	CPU_Dual_Pentium(254),
	CPU_Unknown(255)
		}
		ACCESS read-only
		STATUS mandatory
		DESCRIPTION
			"CPU model"
	::= { hpnsaSiCPUEntry 2 }

	hpnsaSiCPUSpeed OBJECT-TYPE
		SYNTAX INTEGER
		ACCESS read-only
      STATUS mandatory
      DESCRIPTION
	 "CPU speed in MHz."
   ::= { hpnsaSiCPUEntry 3 }

   hpnsaSiOpSysType OBJECT-TYPE
      SYNTAX DisplayString (SIZE (0..255))
      ACCESS read-only
      STATUS mandatory
      DESCRIPTION
	 "Name of the operating system executing on this system,
	 e.g., Microsoft Windows NT, Novell NetWare, etc."
   ::= { hpnsaSiBasicInfo 9 }

   hpnsaSiOpSysVer OBJECT-TYPE
      SYNTAX DisplayString (SIZE (0..255))
      ACCESS read-only
      STATUS mandatory
      DESCRIPTION
	 "Operating system version number string., e.g., 3.1."
   ::= { hpnsaSiBasicInfo 10 }

   hpnsaSiSystemName OBJECT-TYPE
      SYNTAX DisplayString (SIZE (0..255))
      ACCESS read-only
      STATUS mandatory
      DESCRIPTION
	 "Network name of the system, e.g., PAPAYA."
   ::= { hpnsaSiBasicInfo 11 }

   hpnsaSiSystemID OBJECT-TYPE
      SYNTAX DisplayString (SIZE (0..255))
      ACCESS read-only
      STATUS optional
      DESCRIPTION
	 "System ID string that uniquely identifies the system."
   ::= { hpnsaSiBasicInfo 12 }

   hpnsaSiKbdType OBJECT-TYPE
      SYNTAX DisplayString (SIZE (0..255))
      ACCESS read-only
      STATUS optional
      DESCRIPTION
	 "Type of keyboard installed, e.g., U.S., French, German, etc."
   ::= { hpnsaSiBasicInfo 13 }

   hpnsaSiMouseType OBJECT-TYPE
      SYNTAX DisplayString (SIZE (0..255))
      ACCESS read-only
      STATUS optional
      DESCRIPTION
	 "Type of mouse installed, e.g., Microsoft or compatible, etc."
   ::= { hpnsaSiBasicInfo 14 }

   hpnsaSiVideoType OBJECT-TYPE
      SYNTAX DisplayString (SIZE (0..255))
      ACCESS read-only
      STATUS optional
      DESCRIPTION
	 "Type of video installed, e.g., Ultra VGA, Ultra VGA+ etc."
   ::= { hpnsaSiBasicInfo 15 }

   hpnsaSiNumISASlots OBJECT-TYPE
      SYNTAX INTEGER
      ACCESS read-only
      STATUS mandatory
      DESCRIPTION
	 "Number of ISA slots in the system."
   ::= { hpnsaSiBasicInfo 16 }

   hpnsaSiModelName OBJECT-TYPE
     SYNTAX DisplayString (SIZE (0..255))
      ACCESS read-only
      STATUS mandatory
      DESCRIPTION
	 "System Model name"
   ::= { hpnsaSiBasicInfo 17 }

   hpnsaSiOpSysDescription OBJECT-TYPE
      SYNTAX DisplayString (SIZE (0..255))
      ACCESS read-only
      STATUS mandatory
      DESCRIPTION
	 "Additional Operating System information, such as
	 Build Number and Service pack"
   ::= { hpnsaSiBasicInfo 18 }

-- ****************************************************************************
-- HP NSA System Information Security Group
-- ========================================
--
-- hp                                              (1.3.6.1.4.1.11)
--    nm                                           (hp.2)
--       hpnsa                                     (nm.23)
--          hpnsaSystemInfo Group                  (hpnsa.7)
--             hpnsaSiSecurity Group               (hpnsa.7.4)
--                hpnsaSiPowerOnPassword           (hpnsa.7.4.1)
--                hpnsaSiNetServerMode             (hpnsa.7.4.2)
--                hpnsaSiKeyboardLockPassword      (hpnsa.7.4.3)
--                hpnsaSiVideoBlankMode            (hpnsa.7.4.4)
--                hpnsaSiBootDiskPriority          (hpnsa.7.4.5)
--                hpnsaSiWriteToFloppy             (hpnsa.7.4.6)
--                hpnsaSiKbdMouseInactivityTO      (hpnsa.7.4.7)
--
--  The Security group describes how the security features on your HP
--  computer are currently configured.
--
--  Implementation of the security group is mandatory for all agents that
--  support the HP NSA System Information MIB.
--
-- ****************************************************************************

   hpnsaSiPowerOnPassword OBJECT-TYPE
      SYNTAX INTEGER {
	 n-a(0),
	 disabled(1),
	 enabled(2)
      }
      ACCESS read-only
      STATUS mandatory
      DESCRIPTION
	 "The state of the power on password feature."
   ::= { hpnsaSiSecurity 1 }

   hpnsaSiNetServerMode OBJECT-TYPE
      SYNTAX INTEGER {
	 n-a(0),
	 disabled(1),
	 enabled(2)
      }
      ACCESS read-only
      STATUS mandatory
      DESCRIPTION
	 "The state of the network server mode feature."
   ::= { hpnsaSiSecurity 2 }

   hpnsaSiKeyboardLockPassword OBJECT-TYPE
      SYNTAX INTEGER {
	 n-a(0),
	 disabled(1),
	 enabled(2)
      }
      ACCESS read-only
      STATUS mandatory
      DESCRIPTION
	 "The state of the keyboard lock password feature."
   ::= { hpnsaSiSecurity 3 }

   hpnsaSiVideoBlankMode OBJECT-TYPE
      SYNTAX INTEGER {
	 n-a(0),
	 disabled(1),
	 enabled(2)
      }
      ACCESS read-only
      STATUS mandatory
      DESCRIPTION
	 "The state of the blank-screen feature."
   ::= { hpnsaSiSecurity 4 }

   hpnsaSiBootDiskPriority OBJECT-TYPE
      SYNTAX INTEGER {
	 n-a(0),
	 c-then-a(1),
	 a-then-c(2),
	 c-only(3),
	 a-only(4)
      }
      ACCESS read-only
      STATUS mandatory
      DESCRIPTION
	 "Specifies the priority of disks from which the system will boot."
    ::= { hpnsaSiSecurity 5 }

   hpnsaSiWriteToFloppy OBJECT-TYPE
      SYNTAX INTEGER {
	 n-a(0),
	 disabled(1),
	 enabled(2)
      }
      ACCESS read-only
      STATUS mandatory
      DESCRIPTION
	 "Specifies whether one can write to a floppy."
   ::= { hpnsaSiSecurity 6 }

   hpnsaSiKbdMouseInactivityTO OBJECT-TYPE
      SYNTAX INTEGER {
	 n-a(0),
	 disabled(1),
	 enabled(2)
      }
      ACCESS read-only
      STATUS mandatory
      DESCRIPTION
	 "Specifies the state of the keyboard/mouse inactivity timeout feature."
   ::= { hpnsaSiSecurity 7 }

-- ****************************************************************************
-- HP NSA System Information Port Group
-- ====================================
--
-- hp                                              (1.3.6.1.4.1.11)
--    nm                                           (hp.2)
--       hpnsa                                     (nm.23)
--          hpnsaSystemInfo Group                  (hpnsa.7)
--             hpnsaSiPort Group                   (hpnsa.7.5)
--                hpnsaSiPortTable                 (hpnsa.7.5.1)
--                   hpnsaSiPortEntry              (hpnsa.7.5.1.1)
--                      hpnsaSiPortIndex           (hpnsa.7.5.1.1.1)
--                      hpnsaSiPortType            (hpnsa.7.5.1.1.2)
--                      hpnsaSiPortStartAddress    (hpnsa.7.5.1.1.3)
--                      hpnsaSiPortEndAddress      (hpnsa.7.5.1.1.4)
--                      hpnsaSiPortInterruptNum    (hpnsa.7.5.1.1.5)
--
-- The Port group provides information on the system serial and parallel ports
--
-- Implementation of the port group is mandatory for all agents that
-- support the HP NSA System Information MIB.
--
-- ****************************************************************************

   hpnsaSiPortTable OBJECT-TYPE
      SYNTAX SEQUENCE OF HPnsaSiPortEntry
      ACCESS not-accessible
      STATUS mandatory
      DESCRIPTION
	 "A table of port informaton for the system."
   ::= { hpnsaSiPort 1 }

   hpnsaSiPortEntry OBJECT-TYPE
      SYNTAX HPnsaSiPortEntry
      ACCESS not-accessible
      STATUS mandatory
      DESCRIPTION
	 "System port information."
      INDEX { hpnsaSiPortIndex }
   ::= { hpnsaSiPortTable 1 }

   HPnsaSiPortEntry ::= SEQUENCE {
      hpnsaSiPortIndex           INTEGER,
      hpnsaSiPortType            INTEGER,
      hpnsaSiPortStartAddress    INTEGER,
      hpnsaSiPortEndAddress      INTEGER,
      hpnsaSiPortInterruptNum    INTEGER
   }

   hpnsaSiPortIndex OBJECT-TYPE
      SYNTAX INTEGER
      ACCESS read-only
      STATUS mandatory
      DESCRIPTION
	 "A unique port index."
   ::= { hpnsaSiPortEntry 1 }

   hpnsaSiPortType OBJECT-TYPE
      SYNTAX INTEGER {
	 serial(1),
	 parallel(2)
      }
      ACCESS read-only
      STATUS mandatory
      DESCRIPTION
	 "Type of port.  Serial = 1, parallel = 2."
   ::= { hpnsaSiPortEntry 2 }

   hpnsaSiPortStartAddress OBJECT-TYPE
      SYNTAX INTEGER
      ACCESS read-only
      STATUS mandatory
      DESCRIPTION
	 "Port start address."
   ::= { hpnsaSiPortEntry 3 }

   hpnsaSiPortEndAddress OBJECT-TYPE
      SYNTAX INTEGER
      ACCESS read-only
      STATUS mandatory
      DESCRIPTION
	 "Port end address."
   ::= { hpnsaSiPortEntry 4 }

   hpnsaSiPortInterruptNum OBJECT-TYPE
      SYNTAX INTEGER
      ACCESS read-only
      STATUS mandatory
      DESCRIPTION
	 "Interrupt number for this port."
   ::= { hpnsaSiPortEntry 5 }

-- ****************************************************************************
-- HP NSA System Information Memory Table
-- ======================================
--
-- hp                                              (1.3.6.1.4.1.11)
--    nm                                           (hp.2)
--       hpnsa                                     (nm.23)
--          hpnsaSystemInfo Group                  (hpnsa.7)
--             hpnsaSiMemory Group                 (hpnsa.7.6)
--                hpnsaSiBaseMemSize               (hpnsa.7.6.1)
--                hpnsaSiExtMemSize                (hpnsa.7.6.2)
--                hpnsaSiMemType                   (hpnsa.7.6.3)
--                hpnsaSiMemSpeed                  (hpnsa.7.6.4)
--
-- ****************************************************************************

   hpnsaSiBaseMemSize OBJECT-TYPE
      SYNTAX INTEGER (0..2147483647)
      ACCESS read-only
      STATUS mandatory
      DESCRIPTION
	 "Size of base memory installed, in KB."
      ::= { hpnsaSiMemory 1 }

   hpnsaSiExtMemSize OBJECT-TYPE
      SYNTAX INTEGER (0..2147483647)
      ACCESS read-only
      STATUS mandatory
      DESCRIPTION
	 "Size of extended memory installed, in KB."
   ::= { hpnsaSiMemory 2 }

   hpnsaSiMemType OBJECT-TYPE
      SYNTAX INTEGER {
	 other(0),
	 on-board(1),
	 singleWidthModule(2),
	 doubleWidthModule(3),
	 simm(4)
      }
      ACCESS read-only
      STATUS optional
      DESCRIPTION
	 "Type of memory installed.  The value other(0) will be
	  given if the type is not known.  The value board(1) will be
	  given if the memory module is permanently mounted (not modular)
	  on a system board or memory expansion board."
   ::= { hpnsaSiMemory 3 }

   hpnsaSiMemSpeed OBJECT-TYPE
      SYNTAX INTEGER (0..65535)
      ACCESS read-only
      STATUS optional
      DESCRIPTION
	 "Memory speed in nanoseconds.  The value zero (0) will
	  be given if the module speed cannot be determined."
   ::= { hpnsaSiMemory 4 }

-- ****************************************************************************
-- HP NSA System Information Floppy Drive Table
-- ============================================
--
-- hp                                              (1.3.6.1.4.1.11)
--    nm                                           (hp.2)
--       hpnsa                                     (nm.23)
--          hpnsaSystemInfo Group                  (hpnsa.7)
--             hpnsaSiFloppyDrive Group            (hpnsa.7.8)
--                hpnsaSiNumFloppyDrives           (hpnsa.7.8.1)
--                hpnsaSiFloppyDriveTable          (hpnsa.7.8.2)
--                   hpnsaSiFloppyDriveEntry       (hpnsa.7.8.2.1)
--                      hpnsaSiFloppyDriveIndex    (hpnsa.7.8.2.1.1)
--                      hpnsaSiFloppyDriveType     (hpnsa.7.8.2.1.2)
--
-- ****************************************************************************

   hpnsaSiNumFloppyDrives OBJECT-TYPE
      SYNTAX INTEGER
      ACCESS read-only
      STATUS mandatory
      DESCRIPTION
	 "Number of floppy drives installed in the system."
   ::= { hpnsaSiFloppyDrive 1 }

   hpnsaSiFloppyDriveTable OBJECT-TYPE
      SYNTAX SEQUENCE OF HPnsaSiFloppyDriveEntry
      ACCESS not-accessible
      STATUS mandatory
      DESCRIPTION
	 "A table of floppy drive information."
   ::= { hpnsaSiFloppyDrive 2 }

   hpnsaSiFloppyDriveEntry OBJECT-TYPE
      SYNTAX HPnsaSiFloppyDriveEntry
      ACCESS not-accessible
      STATUS mandatory
      DESCRIPTION
	 "Floppy drive information."
      INDEX { hpnsaSiFloppyDriveIndex }
   ::= { hpnsaSiFloppyDriveTable 1 }

   HPnsaSiFloppyDriveEntry ::= SEQUENCE {
      hpnsaSiFloppyDriveIndex     INTEGER,
      hpnsaSiFloppyDriveType      INTEGER
   }

   hpnsaSiFloppyDriveIndex OBJECT-TYPE
      SYNTAX INTEGER
      ACCESS read-only
      STATUS mandatory
      DESCRIPTION
	 "Index of the floppy drive."
   ::= { hpnsaSiFloppyDriveEntry 1 }

   hpnsaSiFloppyDriveType OBJECT-TYPE
      SYNTAX INTEGER {
	 unknown(0),
	 m-360K(1),
	 m-1-2MB(2),
	 m-1-2-MB(3),
	 m-1-44MB(4)
      }
      ACCESS read-only
      STATUS mandatory
      DESCRIPTION
	 "Type of floppy drive."
   ::= { hpnsaSiFloppyDriveEntry 2 }

-- ****************************************************************************
-- HP NSA System Information Remote Locator LED Table
-- ==================================================
--
-- hp                                              (1.3.6.1.4.1.11)
--    nm                                           (hp.2)
--       hpnsa                                     (nm.23)
--          hpnsaSystemInfo Group                  (hpnsa.7)
--             hpnsaSiRemoteLocatorLED Group       (hpnsa.7.9)
--                hpnsaSiRemoteLocatorLEDSupported (hpnsa.7.9.1)
--                hpnsaSiRemoteLocatorLEDStatus    (hpnsa.7.9.2)
--                hpnsaSiRemoteLocatorLEDSet       (hpnsa.7.9.3)
--
-- The RemoteLocatorLED group supports controlling the Remote Locator LED
-- implemented on T11 and later servers.  This LED allows the Identification
-- of a server within a Rack.
--
-- ****************************************************************************

   hpnsaSiRemoteLocatorLEDSupported OBJECT-TYPE
      SYNTAX INTEGER {
	 notSupported(0),
	 Supported(1)
      }
      ACCESS read-only
      STATUS mandatory
      DESCRIPTION
	 "Determines if the Remote Locator LED is implemented on the server."
      ::= { hpnsaSiRemoteLocatorLED 1 }

   hpnsaSiRemoteLocatorLEDStatus OBJECT-TYPE
      SYNTAX INTEGER {
	 ledOFF(0),
	 ledON(1)
      }
      ACCESS read-only
      STATUS mandatory
      DESCRIPTION
	 "Current LED Status.  Value of (0), LED is OFF,
          value of (1), LED is ON."
   ::= { hpnsaSiRemoteLocatorLED 2 }

   hpnsaSiRemoteLocatorLEDSet OBJECT-TYPE
      SYNTAX INTEGER {
	 ledOFF(0),
	 ledON(1)
      }
      ACCESS read-write
      STATUS mandatory
      DESCRIPTION
	 "State to set LED.  Value of (0), turn LED OFF,
          value of (1), turn LED ON."
   ::= { hpnsaSiRemoteLocatorLED 3 }

END
