--  (C) COPYRIGHT HEWLETT-PACKARD COMPANY 2010.
--
--  InkJet IJXXXX Printer Model Specific MIB.
--
--  Generated on 01 Nov 2008
--
--  Company names and product names mentioned herein may be
--  trademarks, and/or registered trademarks of their respective
--  companies.
--
--  For internal and external use.
--
--  This MIB describes all the printer model specific
--  objects supported by the InkJet IJXXXX printer
--  when networked connected using a JetDirect print
--  server.
--
--  The following MIBs also contain objects supported
--  by a JetDirect connected InkJet IJXXXX printer:
--
--  rfc 1514 Host Resources MIB
--  rfc 1759 Printer MIB
--  rfc 1213 MIB II
--
--  This MIB complies with the following RFCs:
--
--  rfc 1157 Simple Network Management Protocol
--  rfc 1155 Structure of Management Information
--
--  Notes:
--
--  1) Objects containing a string which are defined in this MIB use the
--     first two bytes to hold the symbol set used to encode the string.
--     The Roman-8 symbol set has a hex encoding of 0x0115.  Other
--     symbol sets are listed in the PCL 5 Comparison Guide in table
--     C-1 Symbol Set Values.
--
--  2) Some of the objects included are only supported if an accessory
--     is installed.  These accessories include:
--       MIO based accessories
--       SIMM based accessories
--       AT hard disk
--       Paper handling accessories
--       Adobe PostScript accessory
IJXXXX-MIB DEFINITIONS ::= BEGIN
hp OBJECT IDENTIFIER ::= { iso(1) org(3) dod(6) internet(1) private(4) enterprises(1) 11}
dm OBJECT IDENTIFIER ::= { hp nm(2) hpsystem(3) net-peripheral(9) netdm(4) 2}

DisplayString ::= OCTET STRING

device                                 OBJECT IDENTIFIER ::=  { dm 1 } 
device-system                                 OBJECT IDENTIFIER ::=  { device 1 }  

status-system                          OBJECT IDENTIFIER ::=  { device-system 2 }  

test                                   OBJECT IDENTIFIER ::=  { device-system 5 }  

job                                    OBJECT IDENTIFIER ::=  { device-system 6 }  

job-info                               OBJECT IDENTIFIER ::=  { job 5 } 
job-info-accounting                    OBJECT IDENTIFIER ::=  { job-info 28 } 
processing-subsystem                   OBJECT IDENTIFIER ::=  { device 3 } 
pml                                    OBJECT IDENTIFIER ::=  { processing-subsystem 4 } 
accounting                             OBJECT IDENTIFIER ::=  { device-system 16 }  

printer-accounting                     OBJECT IDENTIFIER ::=  { accounting 1 } 
printed-media-usage                    OBJECT IDENTIFIER ::=  { printer-accounting 1 } 
printer-color-accounting               OBJECT IDENTIFIER ::=  { accounting 3 } 
printed-media-color-usage              OBJECT IDENTIFIER ::=  { printer-color-accounting 1 } 
printed-modes-accounting               OBJECT IDENTIFIER ::=  { accounting 4 } 
printed-modes-usage                    OBJECT IDENTIFIER ::=  { printed-modes-accounting 1 } 
source-tray-accounting                 OBJECT IDENTIFIER ::=  { accounting 5 } 
source-tray-usage                      OBJECT IDENTIFIER ::=  { source-tray-accounting 1 } 
destination-bin-accounting             OBJECT IDENTIFIER ::=  { accounting 6 } 
destination-bin-usage                  OBJECT IDENTIFIER ::=  { destination-bin-accounting 1 } 
destination-subsystem                  OBJECT IDENTIFIER ::=  { device 4 } 
print-engine                           OBJECT IDENTIFIER ::=  { destination-subsystem 1 } 
print-media                            OBJECT IDENTIFIER ::=  { print-engine 8 } 
media-size                             OBJECT IDENTIFIER ::=  { print-media 5 } 
background-message                     OBJECT IDENTIFIER ::=  { status-system 37 } 
background-message1                    OBJECT IDENTIFIER ::=  { background-message 1 } 
background-message2                    OBJECT IDENTIFIER ::=  { background-message 2 } 
control-panel-display                  OBJECT IDENTIFIER ::=  { status-system 65 } 
settings-system                        OBJECT IDENTIFIER ::=  { device-system 1 }  

id                                     OBJECT IDENTIFIER ::=  { device-system 3 }  

interface                              OBJECT IDENTIFIER ::=  { device-system 4 }  

simm                                   OBJECT IDENTIFIER ::=  { interface 1 } 
simm1                                  OBJECT IDENTIFIER ::=  { simm 1 } 
simm1-bank                             OBJECT IDENTIFIER ::=  { simm1 6 } 
simm1-bank1                            OBJECT IDENTIFIER ::=  { simm1-bank 1 } 
simm1-bank2                            OBJECT IDENTIFIER ::=  { simm1-bank 2 } 
simm2                                  OBJECT IDENTIFIER ::=  { simm 2 } 
simm2-bank                             OBJECT IDENTIFIER ::=  { simm2 6 } 
simm2-bank1                            OBJECT IDENTIFIER ::=  { simm2-bank 1 } 
simm2-bank2                            OBJECT IDENTIFIER ::=  { simm2-bank 2 } 
settings-job                           OBJECT IDENTIFIER ::=  { job 1 } 
operating-system                       OBJECT IDENTIFIER ::=  { device-system 19 }  

pdl                                    OBJECT IDENTIFIER ::=  { processing-subsystem 3 } 
settings-pdl                           OBJECT IDENTIFIER ::=  { pdl 1 } 
status-pdl                             OBJECT IDENTIFIER ::=  { pdl 2 } 
menus                                  OBJECT IDENTIFIER ::=  { print-engine 13 }  
errorlog                               OBJECT IDENTIFIER ::=  { device-system 11 }  

error1                                 OBJECT IDENTIFIER ::=  { errorlog 1 } 
error2                                 OBJECT IDENTIFIER ::=  { errorlog 2 } 
error3                                 OBJECT IDENTIFIER ::=  { errorlog 3 } 
error4                                 OBJECT IDENTIFIER ::=  { errorlog 4 } 
error5                                 OBJECT IDENTIFIER ::=  { errorlog 5 } 
error6                                 OBJECT IDENTIFIER ::=  { errorlog 6 } 
error7                                 OBJECT IDENTIFIER ::=  { errorlog 7 } 
error8                                 OBJECT IDENTIFIER ::=  { errorlog 8 } 
error9                                 OBJECT IDENTIFIER ::=  { errorlog 9 } 
error10                                OBJECT IDENTIFIER ::=  { errorlog 10 } 
error11                                OBJECT IDENTIFIER ::=  { errorlog 11 } 
error12                                OBJECT IDENTIFIER ::=  { errorlog 12 } 
error13                                OBJECT IDENTIFIER ::=  { errorlog 13 } 
error14                                OBJECT IDENTIFIER ::=  { errorlog 14 } 
error15                                OBJECT IDENTIFIER ::=  { errorlog 15 } 
error16                                OBJECT IDENTIFIER ::=  { errorlog 16 } 
error17                                OBJECT IDENTIFIER ::=  { errorlog 17 } 
error18                                OBJECT IDENTIFIER ::=  { errorlog 18 } 
error19                                OBJECT IDENTIFIER ::=  { errorlog 19 } 
error20                                OBJECT IDENTIFIER ::=  { errorlog 20 } 
error21                                OBJECT IDENTIFIER ::=  { errorlog 21 } 
error22                                OBJECT IDENTIFIER ::=  { errorlog 22 } 
error23                                OBJECT IDENTIFIER ::=  { errorlog 23 } 
error24                                OBJECT IDENTIFIER ::=  { errorlog 24 } 
error25                                OBJECT IDENTIFIER ::=  { errorlog 25 } 
error26                                OBJECT IDENTIFIER ::=  { errorlog 26 } 
error27                                OBJECT IDENTIFIER ::=  { errorlog 27 } 
error28                                OBJECT IDENTIFIER ::=  { errorlog 28 } 
error29                                OBJECT IDENTIFIER ::=  { errorlog 29 } 
error30                                OBJECT IDENTIFIER ::=  { errorlog 30 } 
error31                                OBJECT IDENTIFIER ::=  { errorlog 31 } 
error32                                OBJECT IDENTIFIER ::=  { errorlog 32 } 
error33                                OBJECT IDENTIFIER ::=  { errorlog 33 } 
error34                                OBJECT IDENTIFIER ::=  { errorlog 34 } 
error35                                OBJECT IDENTIFIER ::=  { errorlog 35 } 
error36                                OBJECT IDENTIFIER ::=  { errorlog 36 } 
error37                                OBJECT IDENTIFIER ::=  { errorlog 37 } 
error38                                OBJECT IDENTIFIER ::=  { errorlog 38 } 
error39                                OBJECT IDENTIFIER ::=  { errorlog 39 } 
error40                                OBJECT IDENTIFIER ::=  { errorlog 40 } 
error41                                OBJECT IDENTIFIER ::=  { errorlog 41 } 
error42                                OBJECT IDENTIFIER ::=  { errorlog 42 } 
error43                                OBJECT IDENTIFIER ::=  { errorlog 43 } 
error44                                OBJECT IDENTIFIER ::=  { errorlog 44 } 
error45                                OBJECT IDENTIFIER ::=  { errorlog 45 } 
error46                                OBJECT IDENTIFIER ::=  { errorlog 46 } 
error47                                OBJECT IDENTIFIER ::=  { errorlog 47 } 
error48                                OBJECT IDENTIFIER ::=  { errorlog 48 } 
error49                                OBJECT IDENTIFIER ::=  { errorlog 49 } 
error50                                OBJECT IDENTIFIER ::=  { errorlog 50 } 
error51                                OBJECT IDENTIFIER ::=  { errorlog 51 } 
error52                                OBJECT IDENTIFIER ::=  { errorlog 52 } 
error53                                OBJECT IDENTIFIER ::=  { errorlog 53 } 
error54                                OBJECT IDENTIFIER ::=  { errorlog 54 } 
error55                                OBJECT IDENTIFIER ::=  { errorlog 55 } 
error56                                OBJECT IDENTIFIER ::=  { errorlog 56 } 
error57                                OBJECT IDENTIFIER ::=  { errorlog 57 } 
error58                                OBJECT IDENTIFIER ::=  { errorlog 58 } 
error59                                OBJECT IDENTIFIER ::=  { errorlog 59 } 
error60                                OBJECT IDENTIFIER ::=  { errorlog 60 } 
error61                                OBJECT IDENTIFIER ::=  { errorlog 61 } 
error62                                OBJECT IDENTIFIER ::=  { errorlog 62 } 
error63                                OBJECT IDENTIFIER ::=  { errorlog 63 } 
error64                                OBJECT IDENTIFIER ::=  { errorlog 64 } 
error65                                OBJECT IDENTIFIER ::=  { errorlog 65 } 
error66                                OBJECT IDENTIFIER ::=  { errorlog 66 } 
error67                                OBJECT IDENTIFIER ::=  { errorlog 67 } 
error68                                OBJECT IDENTIFIER ::=  { errorlog 68 } 
error69                                OBJECT IDENTIFIER ::=  { errorlog 69 } 
error70                                OBJECT IDENTIFIER ::=  { errorlog 70 } 
error71                                OBJECT IDENTIFIER ::=  { errorlog 71 } 
error72                                OBJECT IDENTIFIER ::=  { errorlog 72 } 
error73                                OBJECT IDENTIFIER ::=  { errorlog 73 } 
error74                                OBJECT IDENTIFIER ::=  { errorlog 74 } 
error75                                OBJECT IDENTIFIER ::=  { errorlog 75 } 
error76                                OBJECT IDENTIFIER ::=  { errorlog 76 } 
error77                                OBJECT IDENTIFIER ::=  { errorlog 77 } 
error78                                OBJECT IDENTIFIER ::=  { errorlog 78 } 
error79                                OBJECT IDENTIFIER ::=  { errorlog 79 } 
error80                                OBJECT IDENTIFIER ::=  { errorlog 80 } 
error81                                OBJECT IDENTIFIER ::=  { errorlog 81 } 
error82                                OBJECT IDENTIFIER ::=  { errorlog 82 } 
error83                                OBJECT IDENTIFIER ::=  { errorlog 83 } 
error84                                OBJECT IDENTIFIER ::=  { errorlog 84 } 
error85                                OBJECT IDENTIFIER ::=  { errorlog 85 } 
error86                                OBJECT IDENTIFIER ::=  { errorlog 86 } 
error87                                OBJECT IDENTIFIER ::=  { errorlog 87 } 
error88                                OBJECT IDENTIFIER ::=  { errorlog 88 } 
error89                                OBJECT IDENTIFIER ::=  { errorlog 89 } 
error90                                OBJECT IDENTIFIER ::=  { errorlog 90 } 
channel                                OBJECT IDENTIFIER ::=  { device 6 } 
display                                OBJECT IDENTIFIER ::=  { status-system 20 } 
display-status                         OBJECT IDENTIFIER ::=  { display 1 } 
web-server                             OBJECT IDENTIFIER ::=  { interface 6 } 
settings-web-server                    OBJECT IDENTIFIER ::=  { web-server 1 } 
pdl-postscript                         OBJECT IDENTIFIER ::=  { pdl 4 } 
webserver-proc-sub                     OBJECT IDENTIFIER ::=  { processing-subsystem 9 } 
settings-webserver                     OBJECT IDENTIFIER ::=  { webserver-proc-sub 1 } 
settings-prt-eng                       OBJECT IDENTIFIER ::=  { print-engine 1 } 
intray                                 OBJECT IDENTIFIER ::=  { print-engine 3 } 
settings-intray                        OBJECT IDENTIFIER ::=  { intray 1 } 
ph                                     OBJECT IDENTIFIER ::=  { print-engine 7 } 
settings-ph                            OBJECT IDENTIFIER ::=  { ph 1 }  
pdl-pcl                                OBJECT IDENTIFIER ::=  { pdl 3 } 
pdl-pdf                                OBJECT IDENTIFIER ::=  { pdl 15 } 
active-print-jobs                      OBJECT IDENTIFIER ::=  { job 2 } 
job-being-parsed                       OBJECT IDENTIFIER ::=  { active-print-jobs 1 } 
job-info-attribute                     OBJECT IDENTIFIER ::=  { job-info 23 } 
held-job                               OBJECT IDENTIFIER ::=  { job 7 } 
held-job-info                          OBJECT IDENTIFIER ::=  { held-job 1 } 
held-job-control                       OBJECT IDENTIFIER ::=  { held-job 2 } 
source-subsystem                       OBJECT IDENTIFIER ::=  { device 2 } 
spooler                                OBJECT IDENTIFIER ::=  { source-subsystem 4 } 
settings-spooler                       OBJECT IDENTIFIER ::=  { spooler 1 } 
pjl                                    OBJECT IDENTIFIER ::=  { processing-subsystem 5 } 
mio                                    OBJECT IDENTIFIER ::=  { interface 3 } 
mio1                                   OBJECT IDENTIFIER ::=  { mio 1 } 
mio4                                   OBJECT IDENTIFIER ::=  { mio 4 } 
usb-interface                          OBJECT IDENTIFIER ::=  { interface 9 } 
usb                                    OBJECT IDENTIFIER ::=  { usb-interface 2 } 
io                                     OBJECT IDENTIFIER ::=  { source-subsystem 1 } 
settings-io                            OBJECT IDENTIFIER ::=  { io 1 } 
ports                                  OBJECT IDENTIFIER ::=  { io 3 } 
port1                                  OBJECT IDENTIFIER ::=  { ports 1 } 
 

 

tables                                 OBJECT IDENTIFIER ::=  { device 7 } 
remote-procedure-call                  OBJECT IDENTIFIER ::=  { device-system 13 }  

settings-rpc                           OBJECT IDENTIFIER ::=  { remote-procedure-call 1 } 
status-rpc                             OBJECT IDENTIFIER ::=  { remote-procedure-call 2 } 
file-system                            OBJECT IDENTIFIER ::=  { device-system 10 }  

settings-file-system                   OBJECT IDENTIFIER ::=  { file-system 1 } 
file-systems                           OBJECT IDENTIFIER ::=  { file-system 3 } 
file-system2                           OBJECT IDENTIFIER ::=  { file-systems 2 } 
file-system3                           OBJECT IDENTIFIER ::=  { file-systems 3 } 
file-system4                           OBJECT IDENTIFIER ::=  { file-systems 4 } 
resource-manager                       OBJECT IDENTIFIER ::=  { device-system 12 }  

mass-storage-resources                 OBJECT IDENTIFIER ::=  { resource-manager 3 } 
mass-storage-block-driver              OBJECT IDENTIFIER ::=  { device-system 15 }  

settings-mass-storage-bd               OBJECT IDENTIFIER ::=  { mass-storage-block-driver 1 } 
status-mass-storage-bd                 OBJECT IDENTIFIER ::=  { mass-storage-block-driver 2 } 
settings-print-media                   OBJECT IDENTIFIER ::=  { print-media 1 } 
media-info                             OBJECT IDENTIFIER ::=  { print-media 3 } 
media1                                 OBJECT IDENTIFIER ::=  { media-info 1 } 
media2                                 OBJECT IDENTIFIER ::=  { media-info 2 } 
media3                                 OBJECT IDENTIFIER ::=  { media-info 3 } 
media4                                 OBJECT IDENTIFIER ::=  { media-info 4 } 
media5                                 OBJECT IDENTIFIER ::=  { media-info 5 } 
media6                                 OBJECT IDENTIFIER ::=  { media-info 6 } 
media7                                 OBJECT IDENTIFIER ::=  { media-info 7 } 
media8                                 OBJECT IDENTIFIER ::=  { media-info 8 } 
media9                                 OBJECT IDENTIFIER ::=  { media-info 9 } 
media10                                OBJECT IDENTIFIER ::=  { media-info 10 } 
media11                                OBJECT IDENTIFIER ::=  { media-info 11 } 
media12                                OBJECT IDENTIFIER ::=  { media-info 12 } 
media13                                OBJECT IDENTIFIER ::=  { media-info 13 } 
media14                                OBJECT IDENTIFIER ::=  { media-info 14 } 
media15                                OBJECT IDENTIFIER ::=  { media-info 15 } 
media16                                OBJECT IDENTIFIER ::=  { media-info 16 } 
media17                                OBJECT IDENTIFIER ::=  { media-info 17 } 
media18                                OBJECT IDENTIFIER ::=  { media-info 18 } 
media19                                OBJECT IDENTIFIER ::=  { media-info 19 } 
media20                                OBJECT IDENTIFIER ::=  { media-info 20 } 
media21                                OBJECT IDENTIFIER ::=  { media-info 21 } 
media22                                OBJECT IDENTIFIER ::=  { media-info 22 } 
media23                                OBJECT IDENTIFIER ::=  { media-info 23 } 
media24                                OBJECT IDENTIFIER ::=  { media-info 24 } 
media25                                OBJECT IDENTIFIER ::=  { media-info 25 } 
media26                                OBJECT IDENTIFIER ::=  { media-info 26 } 
media27                                OBJECT IDENTIFIER ::=  { media-info 27 } 
media28                                OBJECT IDENTIFIER ::=  { media-info 28 } 
media29                                OBJECT IDENTIFIER ::=  { media-info 29 } 
media30                                OBJECT IDENTIFIER ::=  { media-info 30 } 
media31                                OBJECT IDENTIFIER ::=  { media-info 31 } 
media32                                OBJECT IDENTIFIER ::=  { media-info 32 } 
media33                                OBJECT IDENTIFIER ::=  { media-info 33 } 
media34                                OBJECT IDENTIFIER ::=  { media-info 34 } 
media35                                OBJECT IDENTIFIER ::=  { media-info 35 } 
media36                                OBJECT IDENTIFIER ::=  { media-info 36 } 
media37                                OBJECT IDENTIFIER ::=  { media-info 37 } 
media38                                OBJECT IDENTIFIER ::=  { media-info 38 } 
media-types                            OBJECT IDENTIFIER ::=  { print-media 8 } 
media-sizes                            OBJECT IDENTIFIER ::=  { print-engine 15 } 
device-configure                       OBJECT IDENTIFIER ::=  { settings-system 32 } 
marking-agent-density                  OBJECT IDENTIFIER ::=  { settings-prt-eng 9 } 
status-prt-eng                         OBJECT IDENTIFIER ::=  { print-engine 2 } 
printer-calibration-dhalf              OBJECT IDENTIFIER ::=  { status-prt-eng 37 } 
printer-cal-dhalf-data                 OBJECT IDENTIFIER ::=  { printer-calibration-dhalf 3 } 
printer-cal-grayaxis                   OBJECT IDENTIFIER ::=  { printer-calibration-dhalf 6 } 
printer-cal-grayaxis-data              OBJECT IDENTIFIER ::=  { printer-calibration-dhalf 7 } 
printer-calibration-cpr                OBJECT IDENTIFIER ::=  { status-prt-eng 38 } 
intrays                                OBJECT IDENTIFIER ::=  { intray 3 } 
intray1                                OBJECT IDENTIFIER ::=  { intrays 1 } 
intray2                                OBJECT IDENTIFIER ::=  { intrays 2 } 
intray3                                OBJECT IDENTIFIER ::=  { intrays 3 } 
intray5                                OBJECT IDENTIFIER ::=  { intrays 5 } 
intray6                                OBJECT IDENTIFIER ::=  { intrays 6 } 
outbin                                 OBJECT IDENTIFIER ::=  { print-engine 4 } 
settings-outbin                        OBJECT IDENTIFIER ::=  { outbin 1 } 
outbins                                OBJECT IDENTIFIER ::=  { outbin 3 } 
outbin1                                OBJECT IDENTIFIER ::=  { outbins 1 } 
marking-agent                          OBJECT IDENTIFIER ::=  { print-engine 5 } 
settings-marking-agent                 OBJECT IDENTIFIER ::=  { marking-agent 1 } 
ph-devices                             OBJECT IDENTIFIER ::=  { ph 3 } 
ph2                                    OBJECT IDENTIFIER ::=  { ph-devices 2 } 
media-modes                            OBJECT IDENTIFIER ::=  { print-media 4 } 
media-counts                           OBJECT IDENTIFIER ::=  { print-media 7 } 
consumables                            OBJECT IDENTIFIER ::=  { print-engine 10 } 
consumables-1                          OBJECT IDENTIFIER ::=  { consumables 1 } 
consumable-status                      OBJECT IDENTIFIER ::=  { consumables-1 1 } 
consumable-string                      OBJECT IDENTIFIER ::=  { consumables 8 } 
consumables-status                     OBJECT IDENTIFIER ::=  { consumables 5 } 
consumables-life                       OBJECT IDENTIFIER ::=  { consumables-status 1 } 
print-meter                            OBJECT IDENTIFIER ::=  { print-engine 11 } 
printer-average                        OBJECT IDENTIFIER ::=  { print-meter 1 } 
firmware-download                      OBJECT IDENTIFIER ::=  { device-system 18 }  

upgradable-devices                     OBJECT IDENTIFIER ::=  { device-system 20 }  

print-meter-usage                      OBJECT IDENTIFIER ::=  { printer-accounting 14 }
printer-accounting                     OBJECT IDENTIFIER ::=  { accounting 1 } 
scanner-accounting                     OBJECT IDENTIFIER ::=  { accounting 2 } 



-- 1.3.6.1.4.1.11.2.3.9.4.2.1.1.1.1
energy-star  OBJECT-TYPE
   SYNTAX      integer
   ACCESS      read-write
   STATUS      optional
   DESCRIPTION "Returns or changes the Energy Star sleep value. If the valueis greater than zero, then the device will go into energysaving sleep mode after the print engine has been idle for thenumber of seconds specified by this object. A value of zeromeans Energy Star is disabled and the device will not go tosleep based on print engine idle time. The value must benon-negative. "
   USE " Applications can control the setting of the idle time beforethe device goes to sleep. "
   INTERACTION " If the Energy Star sleep value is positive, then after theprint engine is idle for the specified time, the device willsleep and the SLEEP-MODE object will change to eTrue. May notbe settable if NOT-IDLE contains the cProcessingPDL item. "
   OPERATION " Not destructive."
::= { settings-system 1 }

-- 1.3.6.1.4.1.11.2.3.9.4.2.1.1.1.101
enable-engine-early-warmup  OBJECT-TYPE
   SYNTAX      enumerated { eDisable (1) , eEnable (2) }
   ACCESS      read-write
   STATUS      optional
   DESCRIPTION "This PML object is used by HP SW to enable/disable the printerto send the signal of warm-up process early to engine. Theeffect of warming up early will reduce the First Page Outtime. "
   USE ""
   INTERACTION " ENABLE-ENGINE-EARLY-WARMUP interacts withSTART-ENGINE-EARLY-WARMUP, ENABLE-ENGINE-EARLY-WARMUP willdisable/enable the access of START-ENGINE-EARLY-WARMUP, thedefault setting is eEnable and will survive a power cycle, itwill be set to the default value when we run an NVRAM init,only access by pml "
   OPERATION " Accessing this object identifier is NOT destructive in anymanner."
::= { settings-system 101 }

-- 1.3.6.1.4.1.11.2.3.9.4.2.1.1.1.2
sleep-mode  OBJECT-TYPE
   SYNTAX      enumerated { eFalse (1) , eTrue (2) }
   ACCESS      read-write
   STATUS      optional
   DESCRIPTION "Returns eTrue if the device is in energy saving sleep mode,otherwise returns eFalse. Setting SLEEP-MODE to eFalse causesthe device to wake up, if it is in sleep mode. SettingSLEEP-MODE to eTrue causes the device to go into sleep mode. "
   USE ""
   INTERACTION " May not be settable if NOT-IDLE contains the cProcessingPDLitem. "
   OPERATION " Not destructive."
::= { settings-system 2 }

-- 1.3.6.1.4.1.11.2.3.9.4.2.1.1.1.22
date-display  OBJECT-TYPE
   SYNTAX      enumerated { eDateDisplayMMDDYY (1) , eDateDisplayDDMMYY (2) , eDateDisplayYYMMDD (3) , eDateDisplayMMM-DD-YYYY (4) , eDateDisplayDD-MMM-YYYY (5) , eDateDisplayYYYY-MMM-DD (6) }
   ACCESS      read-write
   STATUS      optional
   DESCRIPTION "Controls front-panel date display format. "
   USE ""
   INTERACTION " None. "
   OPERATION " Not destructive."
::= { settings-system 22 }

-- 1.3.6.1.4.1.11.2.3.9.4.2.1.1.1.31
mono-color-switching-mode  OBJECT-TYPE
   SYNTAX      enumerated { eNeverSwitch (1) , eAlwaysSwitch (2) , eLookAheadSwitch (3) }
   ACCESS      read-write
   STATUS      optional
   DESCRIPTION "This object allows the user to view/change the color/monoswitching mode for a device. "
   USE ""
   INTERACTION " None. "
   OPERATION " Not destructive."
::= { settings-system 31 }

-- 1.3.6.1.4.1.11.2.3.9.4.2.1.1.1.32.12
device-configure-printer-parameters  OBJECT-TYPE
   SYNTAX      string
   ACCESS      read-write
   STATUS      optional
   DESCRIPTION "Allow the printer to be configured as a duplex or simplexprinter. There will be a <<hidden>> encoded in this string anddecoded by the printer firmware. If the <<hidden>> check passesthe printer will be configured accordingly. "
   USE ""
   INTERACTION " None. "
   OPERATION " Not destructive."
::= { device-configure 12 }

-- 1.3.6.1.4.1.11.2.3.9.4.2.1.1.1.43
direct-connect-ports-enable  OBJECT-TYPE
   SYNTAX      enumerated { eFalse (1) , eTrue (2) , eUnSupported (3) }
   ACCESS      read-write
   STATUS      optional
   DESCRIPTION "This object specifies whether all direct connect ports(parallel and USB) are available or ignored. JetDirect,embedded network connectivity, and third party add-on cards(such as Firewire) will be unaffected by setting this object. "
   USE ""
   INTERACTION "  "
   OPERATION " Not destructive."
::= { settings-system 43 }

-- 1.3.6.1.4.1.11.2.3.9.4.2.1.1.1.65
power-state  OBJECT-TYPE
   SYNTAX      enumerated { ePowerStateAwake (1) , ePowerStatePowerSave (2) , ePowerStateSleep (3) , ePowerStateOff (4) , ePowerStateTransitioningToAwake (5) , ePowerStateTransitioningToPowerSave (6) , ePowerStateTransitioningToSleep (7) , ePowerStateTransitioningToOff (8) , ePowerStateReboot (9) , ePowerStateAutoOff (10) , ePowerState1Watt (11) }
   ACCESS      read-write
   STATUS      optional
   DESCRIPTION "This object is used to inquire about and to control the 'powerstate' of the device. The exact meaning of each enumeration mayvary from device to device, but the general interpretation isas follows: ePowerStateAwake: The device is idle (immediatelyready to process a job) or processing a job.ePowerStatePowerSave: The device is in a low power state andwill not be immediately available to process an incoming job. A'warm-up time' of several seconds can be expected.ePowerStateSleep: The device is in a sleep state. It uses lesspower than when in the power save state. It can also beexpected to need a substantially longer warm-up time than whenin the power save state. ePowerStateOff: The device is poweredoff. Note that when the device is powered off then SNMP/PMLrequests obviously cannot be honored. Therefore ePowerStateOffwill likely never be returned from a PML get operation.However, ePowerStateOff could potentially be used in a PML setoperation to power down the device if it has asoftware/firmware controllable power switch. For a givenproduct it may not be possible to have the device enter therequested state due to the current state of the device. E.g.,it may not be possible to enter the power save state if thedevice currently is in the sleep state. In this case a setoperation will have an execution outcome of&lt;ErrorActionCanNotBePerformedNow&gt;. The same execution outcomecan be expected if the device is processing a job and anattempt is made to e.g. bring the device into the power savestate or the sleep state. A get operation on the object returnsthe current power state of the device. While the device istransitioning from one state to another one of the valuesePowerStateTransitioningToAwake,ePowerStateTransitioningToPowerSave,ePowerStateTransitioningToSleep orePowerStateTransitioningToOff will be returned from a PML getoperation. An attempt to perform a PML set with any of thesefour values will yield &lt;ErrorInvalidOrUnsupportedValue&gt;. "
   USE ""
   INTERACTION " There is no required interaction between this object andobjects such as SLEEP-MODE and ENERGY-STAR. The device POS willprovide information as to what the value of e.g. SLEEP-MODEwould be when the device is in any of the states mentionedabove. "
   OPERATION " Not destructive."
::= { settings-system 65 }

-- 1.3.6.1.4.1.11.2.3.9.4.2.1.1.1.68
factory-reset  OBJECT-TYPE
   SYNTAX      integer
   ACCESS      write-only
   STATUS      optional
   DESCRIPTION "writing an integer 0 will do factory reset on device-system variables,MFP Settings and the .NET database without a reboot. "
   USE ""
   INTERACTION " See DESCRIPTION. "
   OPERATION " See DESCRIPTION."
::= { settings-system 68 }

-- 1.3.6.1.4.1.11.2.3.9.4.2.1.1.1.71
order-cartridge  OBJECT-TYPE
   SYNTAX      enumerated { eOff (1) , eOn (2) }
   ACCESS      read-write
   STATUS      optional
   DESCRIPTION "Used to enable/disable the supplies status message that isshown when the supply reaches low. "
   USE ""
   INTERACTION " None "
   OPERATION " Non destructive"
::= { settings-system 71 }

-- 1.3.6.1.4.1.11.2.3.9.4.2.1.1.1.89
powersave-enable-type  OBJECT-TYPE
   SYNTAX      enumerated { ePowerSaveOff (1) , ePowerSaveUseSleepDelay (2) , ePowerSaveUseSleepSchedule (3) , ePowerSaveMaximize (4) , ePowerSaveCustom (5) }
   ACCESS      read-write
   STATUS      optional
   DESCRIPTION "ePowerSaveOff - printer stays awake all the time, can onlysleep if sleep button is hit. ePowerSaveUseSleepDelay - usesleep delay the old way, sleep schedule is ignored .ePowerSaveUseSleepSchedule - sleep delay time is ignored, stayawake in wake period, sleep in 15 minutes in sleep period.ePowerSaveMaximize - set the sleep delay to 15 minutes, sowether in wake or sleep period it will sleep in 15 minutes.ePowerSaveCustom - set the sleep delay to 45 minutes, use sleepdelay during wake period, sleep in 15 minutes in sleep period. "
   USE "  "
   INTERACTION " None. "
   OPERATION " Not Destructive"
::= { settings-system 89 }

-- 1.3.6.1.4.1.11.2.3.9.4.2.1.1.1.97
large-size-media-default-grain-direction  OBJECT-TYPE
   SYNTAX      enumerated { eShortGrain (1) , eLongGrain (2) }
   ACCESS      read-write
   STATUS      optional
   DESCRIPTION "This object identifies default grain direction for large sizemedia (B/A3) only. Default value is eShortGrain. "
   USE ""
   INTERACTION " use eShortGrain(1) and eLongGrain(2). "
   OPERATION " Not Destructive."
::= { settings-system 97 }

-- 1.3.6.1.4.1.11.2.3.9.4.2.1.1.1.99
start-engine-early-warmup  OBJECT-TYPE
   SYNTAX      enumerated { eValue1 (1) }
   ACCESS      write-only
   STATUS      mandatory
   DESCRIPTION "This PML object is used by HP SW drivers to signal the printerthat a job is coming, and to start the warm-up processearly.The effect of warming up early will reduce the First PageOut time. "
   USE ""
   INTERACTION " None. "
   OPERATION " Accessing this object identifier is NOT destructive in anymanner."
::= { settings-system 99}

-- 1.3.6.1.4.1.11.2.3.9.4.2.1.1.11.1.1
error1-time-stamp  OBJECT-TYPE
   SYNTAX      integer
   ACCESS      read-only
   STATUS      optional
   DESCRIPTION "Contains some sort of time stamp indicating when error 1occurred. Example time stamps include the actual time the erroroccurred (in seconds since Jan. 1, 1970), and the total enginepage count. The device POS documents the meaning of the timestamp. "
   USE ""
   INTERACTION " None. "
   OPERATION " Not destructive."
::= { error1 1 }

-- 1.3.6.1.4.1.11.2.3.9.4.2.1.1.11.1.2
error1-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error1 2 }

-- 1.3.6.1.4.1.11.2.3.9.4.2.1.1.11.1.3
error1-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error1 3 }

-- 1.3.6.1.4.1.11.2.3.9.4.2.1.1.11.10.1
error10-time-stamp  OBJECT-TYPE
   SYNTAX      integer
   ACCESS      read-only
   STATUS      optional
   DESCRIPTION "Contains some sort of time stamp indicating when error 10occurred. Example time stamps include the actual time the erroroccurred (in seconds since Jan. 1, 1970), and the total enginepage count. The device POS documents the meaning of the timestamp. "
   USE ""
   INTERACTION " None. "
   OPERATION " Not destructive."
::= { error10 1 }

-- 1.3.6.1.4.1.11.2.3.9.4.2.1.1.11.10.2
error10-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error10 2 }

-- 1.3.6.1.4.1.11.2.3.9.4.2.1.1.11.10.3
error10-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error10 3 }

-- 1.3.6.1.4.1.11.2.3.9.4.2.1.1.11.11.1
error11-time-stamp  OBJECT-TYPE
   SYNTAX      integer
   ACCESS      read-only
   STATUS      optional
   DESCRIPTION "Contains some sort of time stamp indicating when error 11occurred. Example time stamps include the actual time the erroroccurred (in seconds since Jan. 1, 1970), and the total enginepage count. The device POS documents the meaning of the timestamp. "
   USE ""
   INTERACTION " None. "
   OPERATION " Not destructive."
::= { error11 1 }

-- 1.3.6.1.4.1.11.2.3.9.4.2.1.1.11.11.2
error11-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error11 2 }

-- 1.3.6.1.4.1.11.2.3.9.4.2.1.1.11.11.3
error11-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error11 3 }

-- 1.3.6.1.4.1.11.2.3.9.4.2.1.1.11.12.1
error12-time-stamp  OBJECT-TYPE
   SYNTAX      integer
   ACCESS      read-only
   STATUS      optional
   DESCRIPTION "Contains some sort of time stamp indicating when error 12occurred. Example time stamps include the actual time the erroroccurred (in seconds since Jan. 1, 1970), and the total enginepage count. The device POS documents the meaning of the timestamp. "
   USE ""
   INTERACTION " None. "
   OPERATION " Not destructive."
::= { error12 1 }

-- 1.3.6.1.4.1.11.2.3.9.4.2.1.1.11.12.2
error12-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error12 2 }

-- 1.3.6.1.4.1.11.2.3.9.4.2.1.1.11.12.3
error12-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error12 3 }

-- 1.3.6.1.4.1.11.2.3.9.4.2.1.1.11.13.1
error13-time-stamp  OBJECT-TYPE
   SYNTAX      integer
   ACCESS      read-only
   STATUS      optional
   DESCRIPTION "Contains some sort of time stamp indicating when error 13occurred. Example time stamps include the actual time the erroroccurred (in seconds since Jan. 1, 1970), and the total enginepage count. The device POS documents the meaning of the timestamp. "
   USE ""
   INTERACTION " None. "
   OPERATION " Not destructive."
::= { error13 1 }

-- 1.3.6.1.4.1.11.2.3.9.4.2.1.1.11.13.2
error13-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error13 2 }

-- 1.3.6.1.4.1.11.2.3.9.4.2.1.1.11.13.3
error13-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error13 3 }

-- 1.3.6.1.4.1.11.2.3.9.4.2.1.1.11.14.1
error14-time-stamp  OBJECT-TYPE
   SYNTAX      integer
   ACCESS      read-only
   STATUS      optional
   DESCRIPTION "Contains some sort of time stamp indicating when error 14occurred. Example time stamps include the actual time the erroroccurred (in seconds since Jan. 1, 1970), and the total enginepage count. The device POS documents the meaning of the timestamp. "
   USE ""
   INTERACTION " None. "
   OPERATION " Not destructive."
::= { error14 1 }

-- 1.3.6.1.4.1.11.2.3.9.4.2.1.1.11.14.2
error14-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error14 2 }

-- 1.3.6.1.4.1.11.2.3.9.4.2.1.1.11.14.3
error14-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error14 3 }

-- 1.3.6.1.4.1.11.2.3.9.4.2.1.1.11.15.1
error15-time-stamp  OBJECT-TYPE
   SYNTAX      integer
   ACCESS      read-only
   STATUS      optional
   DESCRIPTION "Contains some sort of time stamp indicating when error 15occurred. Example time stamps include the actual time the erroroccurred (in seconds since Jan. 1, 1970), and the total enginepage count. The device POS documents the meaning of the timestamp. "
   USE ""
   INTERACTION " None. "
   OPERATION " Not destructive."
::= { error15 1 }

-- 1.3.6.1.4.1.11.2.3.9.4.2.1.1.11.15.2
error15-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error15 2 }

-- 1.3.6.1.4.1.11.2.3.9.4.2.1.1.11.15.3
error15-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error15 3 }

-- 1.3.6.1.4.1.11.2.3.9.4.2.1.1.11.16.1
error16-time-stamp  OBJECT-TYPE
   SYNTAX      integer
   ACCESS      read-only
   STATUS      optional
   DESCRIPTION "Contains some sort of time stamp indicating when error 16occurred. Example time stamps include the actual time the erroroccurred (in seconds since Jan. 1, 1970), and the total enginepage count. The device POS documents the meaning of the timestamp. "
   USE ""
   INTERACTION " None. "
   OPERATION " Not destructive."
::= { error16 1 }

-- 1.3.6.1.4.1.11.2.3.9.4.2.1.1.11.16.2
error16-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error16 2 }

-- 1.3.6.1.4.1.11.2.3.9.4.2.1.1.11.16.3
error16-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error16 3 }

-- 1.3.6.1.4.1.11.2.3.9.4.2.1.1.11.17.1
error17-time-stamp  OBJECT-TYPE
   SYNTAX      integer
   ACCESS      read-only
   STATUS      optional
   DESCRIPTION "Contains some sort of time stamp indicating when error 17occurred. Example time stamps include the actual time the erroroccurred (in seconds since Jan. 1, 1970), and the total enginepage count. The device POS documents the meaning of the timestamp. "
   USE ""
   INTERACTION " None. "
   OPERATION " Not destructive."
::= { error17 1 }

-- 1.3.6.1.4.1.11.2.3.9.4.2.1.1.11.17.2
error17-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error17 2 }

-- 1.3.6.1.4.1.11.2.3.9.4.2.1.1.11.17.3
error17-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error17 3 }

-- 1.3.6.1.4.1.11.2.3.9.4.2.1.1.11.18.1
error18-time-stamp  OBJECT-TYPE
   SYNTAX      integer
   ACCESS      read-only
   STATUS      optional
   DESCRIPTION "Contains some sort of time stamp indicating when error 18occurred. Example time stamps include the actual time the erroroccurred (in seconds since Jan. 1, 1970), and the total enginepage count. The device POS documents the meaning of the timestamp. "
   USE ""
   INTERACTION " None. "
   OPERATION " Not destructive."
::= { error18 1 }

-- 1.3.6.1.4.1.11.2.3.9.4.2.1.1.11.18.2
error18-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error18 2 }

-- 1.3.6.1.4.1.11.2.3.9.4.2.1.1.11.18.3
error18-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error18 3 }

-- 1.3.6.1.4.1.11.2.3.9.4.2.1.1.11.19.1
error19-time-stamp  OBJECT-TYPE
   SYNTAX      integer
   ACCESS      read-only
   STATUS      optional
   DESCRIPTION "Contains some sort of time stamp indicating when error 19occurred. Example time stamps include the actual time the erroroccurred (in seconds since Jan. 1, 1970), and the total enginepage count. The device POS documents the meaning of the timestamp. "
   USE ""
   INTERACTION " None. "
   OPERATION " Not destructive."
::= { error19 1 }

-- 1.3.6.1.4.1.11.2.3.9.4.2.1.1.11.19.2
error19-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error19 2 }

-- 1.3.6.1.4.1.11.2.3.9.4.2.1.1.11.19.3
error19-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error19 3 }

-- 1.3.6.1.4.1.11.2.3.9.4.2.1.1.11.2.1
error2-time-stamp  OBJECT-TYPE
   SYNTAX      integer
   ACCESS      read-only
   STATUS      optional
   DESCRIPTION "Contains some sort of time stamp indicating when error 2occurred. Example time stamps include the actual time the erroroccurred (in seconds since Jan. 1, 1970), and the total enginepage count. The device POS documents the meaning of the timestamp. "
   USE ""
   INTERACTION " None. "
   OPERATION " Not destructive."
::= { error2 1 }

-- 1.3.6.1.4.1.11.2.3.9.4.2.1.1.11.2.2
error2-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error2 2 }

-- 1.3.6.1.4.1.11.2.3.9.4.2.1.1.11.2.3
error2-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error2 3 }

-- 1.3.6.1.4.1.11.2.3.9.4.2.1.1.11.20.1
error20-time-stamp  OBJECT-TYPE
   SYNTAX      integer
   ACCESS      read-only
   STATUS      optional
   DESCRIPTION "Contains some sort of time stamp indicating when error 20occurred. Example time stamps include the actual time the erroroccurred (in seconds since Jan. 1, 1970), and the total enginepage count. The device POS documents the meaning of the timestamp. "
   USE ""
   INTERACTION " None. "
   OPERATION " Not destructive."
::= { error20 1 }

-- 1.3.6.1.4.1.11.2.3.9.4.2.1.1.11.20.2
error20-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error20 2 }

-- 1.3.6.1.4.1.11.2.3.9.4.2.1.1.11.20.3
error20-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error20 3 }

-- 1.3.6.1.4.1.11.2.3.9.4.2.1.1.11.21.1
error21-time-stamp  OBJECT-TYPE
   SYNTAX      integer
   ACCESS      read-only
   STATUS      optional
   DESCRIPTION "Contains some sort of time stamp indicating when error 21occurred. Example time stamps include the actual time the erroroccurred (in seconds since Jan. 1, 1970), and the total enginepage count. The device POS documents the meaning of the timestamp. "
   USE ""
   INTERACTION " None. "
   OPERATION " Not destructive."
::= { error21 1 }

-- 1.3.6.1.4.1.11.2.3.9.4.2.1.1.11.21.2
error21-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error21 2 }

-- 1.3.6.1.4.1.11.2.3.9.4.2.1.1.11.21.3
error21-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error21 3 }

-- 1.3.6.1.4.1.11.2.3.9.4.2.1.1.11.22.1
error22-time-stamp  OBJECT-TYPE
   SYNTAX      integer
   ACCESS      read-only
   STATUS      optional
   DESCRIPTION "Contains some sort of time stamp indicating when error 22occurred. Example time stamps include the actual time the erroroccurred (in seconds since Jan. 1, 1970), and the total enginepage count. The device POS documents the meaning of the timestamp. "
   USE ""
   INTERACTION " None. "
   OPERATION " Not destructive."
::= { error22 1 }

-- 1.3.6.1.4.1.11.2.3.9.4.2.1.1.11.22.2
error22-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error22 2 }

-- 1.3.6.1.4.1.11.2.3.9.4.2.1.1.11.22.3
error22-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error22 3 }

-- 1.3.6.1.4.1.11.2.3.9.4.2.1.1.11.23.1
error23-time-stamp  OBJECT-TYPE
   SYNTAX      integer
   ACCESS      read-only
   STATUS      optional
   DESCRIPTION "Contains some sort of time stamp indicating when error 23occurred. Example time stamps include the actual time the erroroccurred (in seconds since Jan. 1, 1970), and the total enginepage count. The device POS documents the meaning of the timestamp. "
   USE ""
   INTERACTION " None. "
   OPERATION " Not destructive."
::= { error23 1 }

-- 1.3.6.1.4.1.11.2.3.9.4.2.1.1.11.23.2
error23-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error23 2 }

-- 1.3.6.1.4.1.11.2.3.9.4.2.1.1.11.23.3
error23-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error23 3 }

-- 1.3.6.1.4.1.11.2.3.9.4.2.1.1.11.24.1
error24-time-stamp  OBJECT-TYPE
   SYNTAX      integer
   ACCESS      read-only
   STATUS      optional
   DESCRIPTION "Contains some sort of time stamp indicating when error 24occurred. Example time stamps include the actual time the erroroccurred (in seconds since Jan. 1, 1970), and the total enginepage count. The device POS documents the meaning of the timestamp. "
   USE ""
   INTERACTION " None. "
   OPERATION " Not destructive."
::= { error24 1 }

-- 1.3.6.1.4.1.11.2.3.9.4.2.1.1.11.24.2
error24-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error24 2 }

-- 1.3.6.1.4.1.11.2.3.9.4.2.1.1.11.24.3
error24-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error24 3 }

-- 1.3.6.1.4.1.11.2.3.9.4.2.1.1.11.25.1
error25-time-stamp  OBJECT-TYPE
   SYNTAX      integer
   ACCESS      read-only
   STATUS      optional
   DESCRIPTION "Contains some sort of time stamp indicating when error 25occurred. Example time stamps include the actual time the erroroccurred (in seconds since Jan. 1, 1970), and the total enginepage count. The device POS documents the meaning of the timestamp. "
   USE ""
   INTERACTION " None. "
   OPERATION " Not destructive."
::= { error25 1 }

-- 1.3.6.1.4.1.11.2.3.9.4.2.1.1.11.25.2
error25-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error25 2 }

-- 1.3.6.1.4.1.11.2.3.9.4.2.1.1.11.25.3
error25-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error25 3 }

-- 1.3.6.1.4.1.11.2.3.9.4.2.1.1.11.26.1
error26-time-stamp  OBJECT-TYPE
   SYNTAX      integer
   ACCESS      read-only
   STATUS      optional
   DESCRIPTION "Contains some sort of time stamp indicating when error 26occurred. Example time stamps include the actual time the erroroccurred (in seconds since Jan. 1, 1970), and the total enginepage count. The device POS documents the meaning of the timestamp. "
   USE ""
   INTERACTION " None. "
   OPERATION " Not destructive."
::= { error26 1 }

-- 1.3.6.1.4.1.11.2.3.9.4.2.1.1.11.26.2
error26-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error26 2 }

-- 1.3.6.1.4.1.11.2.3.9.4.2.1.1.11.26.3
error26-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error26 3 }

-- 1.3.6.1.4.1.11.2.3.9.4.2.1.1.11.27.1
error27-time-stamp  OBJECT-TYPE
   SYNTAX      integer
   ACCESS      read-only
   STATUS      optional
   DESCRIPTION "Contains some sort of time stamp indicating when error 27occurred. Example time stamps include the actual time the erroroccurred (in seconds since Jan. 1, 1970), and the total enginepage count. The device POS documents the meaning of the timestamp. "
   USE ""
   INTERACTION " None. "
   OPERATION " Not destructive."
::= { error27 1 }

-- 1.3.6.1.4.1.11.2.3.9.4.2.1.1.11.27.2
error27-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error27 2 }

-- 1.3.6.1.4.1.11.2.3.9.4.2.1.1.11.27.3
error27-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error27 3 }

-- 1.3.6.1.4.1.11.2.3.9.4.2.1.1.11.28.1
error28-time-stamp  OBJECT-TYPE
   SYNTAX      integer
   ACCESS      read-only
   STATUS      optional
   DESCRIPTION "Contains some sort of time stamp indicating when error 28occurred. Example time stamps include the actual time the erroroccurred (in seconds since Jan. 1, 1970), and the total enginepage count. The device POS documents the meaning of the timestamp. "
   USE ""
   INTERACTION " None. "
   OPERATION " Not destructive."
::= { error28 1 }

-- 1.3.6.1.4.1.11.2.3.9.4.2.1.1.11.28.2
error28-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error28 2 }

-- 1.3.6.1.4.1.11.2.3.9.4.2.1.1.11.28.3
error28-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error28 3 }

-- 1.3.6.1.4.1.11.2.3.9.4.2.1.1.11.29.1
error29-time-stamp  OBJECT-TYPE
   SYNTAX      integer
   ACCESS      read-only
   STATUS      optional
   DESCRIPTION "Contains some sort of time stamp indicating when error 29occurred. Example time stamps include the actual time the erroroccurred (in seconds since Jan. 1, 1970), and the total enginepage count. The device POS documents the meaning of the timestamp. "
   USE ""
   INTERACTION " None. "
   OPERATION " Not destructive."
::= { error29 1 }

-- 1.3.6.1.4.1.11.2.3.9.4.2.1.1.11.29.2
error29-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error29 2 }

-- 1.3.6.1.4.1.11.2.3.9.4.2.1.1.11.29.3
error29-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error29 3 }

-- 1.3.6.1.4.1.11.2.3.9.4.2.1.1.11.3.1
error3-time-stamp  OBJECT-TYPE
   SYNTAX      integer
   ACCESS      read-only
   STATUS      optional
   DESCRIPTION "Contains some sort of time stamp indicating when error 3occurred. Example time stamps include the actual time the erroroccurred (in seconds since Jan. 1, 1970), and the total enginepage count. The device POS documents the meaning of the timestamp. "
   USE ""
   INTERACTION " None. "
   OPERATION " Not destructive."
::= { error3 1 }

-- 1.3.6.1.4.1.11.2.3.9.4.2.1.1.11.3.2
error3-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error3 2 }

-- 1.3.6.1.4.1.11.2.3.9.4.2.1.1.11.3.3
error3-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error3 3 }

-- 1.3.6.1.4.1.11.2.3.9.4.2.1.1.11.30.1
error30-time-stamp  OBJECT-TYPE
   SYNTAX      integer
   ACCESS      read-only
   STATUS      optional
   DESCRIPTION "Contains some sort of time stamp indicating when error 30occurred. Example time stamps include the actual time the erroroccurred (in seconds since Jan. 1, 1970), and the total enginepage count. The device POS documents the meaning of the timestamp. "
   USE ""
   INTERACTION " None. "
   OPERATION " Not destructive."
::= { error30 1 }

-- 1.3.6.1.4.1.11.2.3.9.4.2.1.1.11.30.2
error30-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error30 2 }

-- 1.3.6.1.4.1.11.2.3.9.4.2.1.1.11.30.3
error30-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error30 3 }

-- 1.3.6.1.4.1.11.2.3.9.4.2.1.1.11.31.1
error31-time-stamp  OBJECT-TYPE
   SYNTAX      integer
   ACCESS      read-only
   STATUS      optional
   DESCRIPTION "Contains some sort of time stamp indicating when error 31occurred. Example time stamps include the actual time the erroroccurred (in seconds since Jan. 1, 1970), and the total enginepage count. The device POS documents the meaning of the timestamp. "
   USE ""
   INTERACTION " None. "
   OPERATION " Not destructive."
::= { error31 1 }

-- 1.3.6.1.4.1.11.2.3.9.4.2.1.1.11.31.2
error31-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error31 2 }

-- 1.3.6.1.4.1.11.2.3.9.4.2.1.1.11.31.3
error31-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error31 3 }

-- 1.3.6.1.4.1.11.2.3.9.4.2.1.1.11.32.1
error32-time-stamp  OBJECT-TYPE
   SYNTAX      integer
   ACCESS      read-only
   STATUS      optional
   DESCRIPTION "Contains some sort of time stamp indicating when error 32occurred. Example time stamps include the actual time the erroroccurred (in seconds since Jan. 1, 1970), and the total enginepage count. The device POS documents the meaning of the timestamp. "
   USE ""
   INTERACTION " None. "
   OPERATION " Not destructive."
::= { error32 1 }

-- 1.3.6.1.4.1.11.2.3.9.4.2.1.1.11.32.2
error32-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error32 2 }

-- 1.3.6.1.4.1.11.2.3.9.4.2.1.1.11.32.3
error32-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error32 3 }

-- 1.3.6.1.4.1.11.2.3.9.4.2.1.1.11.33.1
error33-time-stamp  OBJECT-TYPE
   SYNTAX      integer
   ACCESS      read-only
   STATUS      optional
   DESCRIPTION "Contains some sort of time stamp indicating when error 33occurred. Example time stamps include the actual time the erroroccurred (in seconds since Jan. 1, 1970), and the total enginepage count. The device POS documents the meaning of the timestamp. "
   USE ""
   INTERACTION " None. "
   OPERATION " Not destructive."
::= { error33 1 }

-- 1.3.6.1.4.1.11.2.3.9.4.2.1.1.11.33.2
error33-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error33 2 }

-- 1.3.6.1.4.1.11.2.3.9.4.2.1.1.11.33.3
error33-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error33 3 }

-- 1.3.6.1.4.1.11.2.3.9.4.2.1.1.11.34.1
error34-time-stamp  OBJECT-TYPE
   SYNTAX      integer
   ACCESS      read-only
   STATUS      optional
   DESCRIPTION "Contains some sort of time stamp indicating when error 34occurred. Example time stamps include the actual time the erroroccurred (in seconds since Jan. 1, 1970), and the total enginepage count. The device POS documents the meaning of the timestamp. "
   USE ""
   INTERACTION " None. "
   OPERATION " Not destructive."
::= { error34 1 }

-- 1.3.6.1.4.1.11.2.3.9.4.2.1.1.11.34.2
error34-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error34 2 }

-- 1.3.6.1.4.1.11.2.3.9.4.2.1.1.11.34.3
error34-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error34 3 }

-- 1.3.6.1.4.1.11.2.3.9.4.2.1.1.11.35.1
error35-time-stamp  OBJECT-TYPE
   SYNTAX      integer
   ACCESS      read-only
   STATUS      optional
   DESCRIPTION "Contains some sort of time stamp indicating when error 35occurred. Example time stamps include the actual time the erroroccurred (in seconds since Jan. 1, 1970), and the total enginepage count. The device POS documents the meaning of the timestamp. "
   USE ""
   INTERACTION " None. "
   OPERATION " Not destructive."
::= { error35 1 }

-- 1.3.6.1.4.1.11.2.3.9.4.2.1.1.11.35.2
error35-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error35 2 }

-- 1.3.6.1.4.1.11.2.3.9.4.2.1.1.11.35.3
error35-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error35 3 }

-- 1.3.6.1.4.1.11.2.3.9.4.2.1.1.11.36.1
error36-time-stamp  OBJECT-TYPE
   SYNTAX      integer
   ACCESS      read-only
   STATUS      optional
   DESCRIPTION "Contains some sort of time stamp indicating when error 36occurred. Example time stamps include the actual time the erroroccurred (in seconds since Jan. 1, 1970), and the total enginepage count. The device POS documents the meaning of the timestamp. "
   USE ""
   INTERACTION " None. "
   OPERATION " Not destructive."
::= { error36 1 }

-- 1.3.6.1.4.1.11.2.3.9.4.2.1.1.11.36.2
error36-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error36 2 }

-- 1.3.6.1.4.1.11.2.3.9.4.2.1.1.11.36.3
error36-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error36 3 }

-- 1.3.6.1.4.1.11.2.3.9.4.2.1.1.11.37.1
error37-time-stamp  OBJECT-TYPE
   SYNTAX      integer
   ACCESS      read-only
   STATUS      optional
   DESCRIPTION "Contains some sort of time stamp indicating when error 37occurred. Example time stamps include the actual time the erroroccurred (in seconds since Jan. 1, 1970), and the total enginepage count. The device POS documents the meaning of the timestamp. "
   USE ""
   INTERACTION " None. "
   OPERATION " Not destructive."
::= { error37 1 }

-- 1.3.6.1.4.1.11.2.3.9.4.2.1.1.11.37.2
error37-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error37 2 }

-- 1.3.6.1.4.1.11.2.3.9.4.2.1.1.11.37.3
error37-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error37 3 }

-- 1.3.6.1.4.1.11.2.3.9.4.2.1.1.11.38.1
error38-time-stamp  OBJECT-TYPE
   SYNTAX      integer
   ACCESS      read-only
   STATUS      optional
   DESCRIPTION "Contains some sort of time stamp indicating when error 38occurred. Example time stamps include the actual time the erroroccurred (in seconds since Jan. 1, 1970), and the total enginepage count. The device POS documents the meaning of the timestamp. "
   USE ""
   INTERACTION " None. "
   OPERATION " Not destructive."
::= { error38 1 }

-- 1.3.6.1.4.1.11.2.3.9.4.2.1.1.11.38.2
error38-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error38 2 }

-- 1.3.6.1.4.1.11.2.3.9.4.2.1.1.11.38.3
error38-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error38 3 }

-- 1.3.6.1.4.1.11.2.3.9.4.2.1.1.11.39.1
error39-time-stamp  OBJECT-TYPE
   SYNTAX      integer
   ACCESS      read-only
   STATUS      optional
   DESCRIPTION "Contains some sort of time stamp indicating when error 39occurred. Example time stamps include the actual time the erroroccurred (in seconds since Jan. 1, 1970), and the total enginepage count. The device POS documents the meaning of the timestamp. "
   USE ""
   INTERACTION " None. "
   OPERATION " Not destructive."
::= { error39 1 }

-- 1.3.6.1.4.1.11.2.3.9.4.2.1.1.11.39.2
error39-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error39 2 }

-- 1.3.6.1.4.1.11.2.3.9.4.2.1.1.11.39.3
error39-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error39 3 }

-- 1.3.6.1.4.1.11.2.3.9.4.2.1.1.11.4.1
error4-time-stamp  OBJECT-TYPE
   SYNTAX      integer
   ACCESS      read-only
   STATUS      optional
   DESCRIPTION "Contains some sort of time stamp indicating when error 4occurred. Example time stamps include the actual time the erroroccurred (in seconds since Jan. 1, 1970), and the total enginepage count. The device POS documents the meaning of the timestamp. "
   USE ""
   INTERACTION " None. "
   OPERATION " Not destructive."
::= { error4 1 }

-- 1.3.6.1.4.1.11.2.3.9.4.2.1.1.11.4.2
error4-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error4 2 }

-- 1.3.6.1.4.1.11.2.3.9.4.2.1.1.11.4.3
error4-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error4 3 }

-- 1.3.6.1.4.1.11.2.3.9.4.2.1.1.11.40.1
error40-time-stamp  OBJECT-TYPE
   SYNTAX      integer
   ACCESS      read-only
   STATUS      optional
   DESCRIPTION "Contains some sort of time stamp indicating when error 40occurred. Example time stamps include the actual time the erroroccurred (in seconds since Jan. 1, 1970), and the total enginepage count. The device POS documents the meaning of the timestamp. "
   USE ""
   INTERACTION " None. "
   OPERATION " Not destructive."
::= { error40 1 }

-- 1.3.6.1.4.1.11.2.3.9.4.2.1.1.11.40.2
error40-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error40 2 }

-- 1.3.6.1.4.1.11.2.3.9.4.2.1.1.11.40.3
error40-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error40 3 }

-- 1.3.6.1.4.1.11.2.3.9.4.2.1.1.11.41.1
error41-time-stamp  OBJECT-TYPE
   SYNTAX      integer
   ACCESS      read-only
   STATUS      optional
   DESCRIPTION "Contains some sort of time stamp indicating when error 41occurred. Example time stamps include the actual time the erroroccurred (in seconds since Jan. 1, 1970), and the total enginepage count. The device POS documents the meaning of the timestamp. "
   USE ""
   INTERACTION " None. "
   OPERATION " Not destructive."
::= { error41 1 }

-- 1.3.6.1.4.1.11.2.3.9.4.2.1.1.11.41.2
error41-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error41 2 }

-- 1.3.6.1.4.1.11.2.3.9.4.2.1.1.11.41.3
error41-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error41 3 }

-- 1.3.6.1.4.1.11.2.3.9.4.2.1.1.11.42.1
error42-time-stamp  OBJECT-TYPE
   SYNTAX      integer
   ACCESS      read-only
   STATUS      optional
   DESCRIPTION "Contains some sort of time stamp indicating when error 42occurred. Example time stamps include the actual time the erroroccurred (in seconds since Jan. 1, 1970), and the total enginepage count. The device POS documents the meaning of the timestamp. "
   USE ""
   INTERACTION " None. "
   OPERATION " Not destructive."
::= { error42 1 }

-- 1.3.6.1.4.1.11.2.3.9.4.2.1.1.11.42.2
error42-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error42 2 }

-- 1.3.6.1.4.1.11.2.3.9.4.2.1.1.11.42.3
error42-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error42 3 }

-- 1.3.6.1.4.1.11.2.3.9.4.2.1.1.11.43.1
error43-time-stamp  OBJECT-TYPE
   SYNTAX      integer
   ACCESS      read-only
   STATUS      optional
   DESCRIPTION "Contains some sort of time stamp indicating when error 43occurred. Example time stamps include the actual time the erroroccurred (in seconds since Jan. 1, 1970), and the total enginepage count. The device POS documents the meaning of the timestamp. "
   USE ""
   INTERACTION " None. "
   OPERATION " Not destructive."
::= { error43 1 }

-- 1.3.6.1.4.1.11.2.3.9.4.2.1.1.11.43.2
error43-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error43 2 }

-- 1.3.6.1.4.1.11.2.3.9.4.2.1.1.11.43.3
error43-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error43 3 }

-- 1.3.6.1.4.1.11.2.3.9.4.2.1.1.11.44.1
error44-time-stamp  OBJECT-TYPE
   SYNTAX      integer
   ACCESS      read-only
   STATUS      optional
   DESCRIPTION "Contains some sort of time stamp indicating when error 44occurred. Example time stamps include the actual time the erroroccurred (in seconds since Jan. 1, 1970), and the total enginepage count. The device POS documents the meaning of the timestamp. "
   USE ""
   INTERACTION " None. "
   OPERATION " Not destructive."
::= { error44 1 }

-- 1.3.6.1.4.1.11.2.3.9.4.2.1.1.11.44.2
error44-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error44 2 }

-- 1.3.6.1.4.1.11.2.3.9.4.2.1.1.11.44.3
error44-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error44 3 }

-- 1.3.6.1.4.1.11.2.3.9.4.2.1.1.11.45.1
error45-time-stamp  OBJECT-TYPE
   SYNTAX      integer
   ACCESS      read-only
   STATUS      optional
   DESCRIPTION "Contains some sort of time stamp indicating when error 45occurred. Example time stamps include the actual time the erroroccurred (in seconds since Jan. 1, 1970), and the total enginepage count. The device POS documents the meaning of the timestamp. "
   USE ""
   INTERACTION " None. "
   OPERATION " Not destructive."
::= { error45 1 }

-- 1.3.6.1.4.1.11.2.3.9.4.2.1.1.11.45.2
error45-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error45 2 }

-- 1.3.6.1.4.1.11.2.3.9.4.2.1.1.11.45.3
error45-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error45 3 }

-- 1.3.6.1.4.1.11.2.3.9.4.2.1.1.11.46.1
error46-time-stamp  OBJECT-TYPE
   SYNTAX      integer
   ACCESS      read-only
   STATUS      optional
   DESCRIPTION "Contains some sort of time stamp indicating when error 46occurred. Example time stamps include the actual time the erroroccurred (in seconds since Jan. 1, 1970), and the total enginepage count. The device POS documents the meaning of the timestamp. "
   USE ""
   INTERACTION " None. "
   OPERATION " Not destructive."
::= { error46 1 }

-- 1.3.6.1.4.1.11.2.3.9.4.2.1.1.11.46.2
error46-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error46 2 }

-- 1.3.6.1.4.1.11.2.3.9.4.2.1.1.11.46.3
error46-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error46 3 }

-- 1.3.6.1.4.1.11.2.3.9.4.2.1.1.11.47.1
error47-time-stamp  OBJECT-TYPE
   SYNTAX      integer
   ACCESS      read-only
   STATUS      optional
   DESCRIPTION "Contains some sort of time stamp indicating when error 47occurred. Example time stamps include the actual time the erroroccurred (in seconds since Jan. 1, 1970), and the total enginepage count. The device POS documents the meaning of the timestamp. "
   USE ""
   INTERACTION " None. "
   OPERATION " Not destructive."
::= { error47 1 }

-- 1.3.6.1.4.1.11.2.3.9.4.2.1.1.11.47.2
error47-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error47 2 }

-- 1.3.6.1.4.1.11.2.3.9.4.2.1.1.11.47.3
error47-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error47 3 }

-- 1.3.6.1.4.1.11.2.3.9.4.2.1.1.11.48.1
error48-time-stamp  OBJECT-TYPE
   SYNTAX      integer
   ACCESS      read-only
   STATUS      optional
   DESCRIPTION "Contains some sort of time stamp indicating when error 48occurred. Example time stamps include the actual time the erroroccurred (in seconds since Jan. 1, 1970), and the total enginepage count. The device POS documents the meaning of the timestamp. "
   USE ""
   INTERACTION " None. "
   OPERATION " Not destructive."
::= { error48 1 }

-- 1.3.6.1.4.1.11.2.3.9.4.2.1.1.11.48.2
error48-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error48 2 }

-- 1.3.6.1.4.1.11.2.3.9.4.2.1.1.11.48.3
error48-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error48 3 }

-- 1.3.6.1.4.1.11.2.3.9.4.2.1.1.11.49.1
error49-time-stamp  OBJECT-TYPE
   SYNTAX      integer
   ACCESS      read-only
   STATUS      optional
   DESCRIPTION "Contains some sort of time stamp indicating when error 49occurred. Example time stamps include the actual time the erroroccurred (in seconds since Jan. 1, 1970), and the total enginepage count. The device POS documents the meaning of the timestamp. "
   USE ""
   INTERACTION " None. "
   OPERATION " Not destructive."
::= { error49 1 }

-- 1.3.6.1.4.1.11.2.3.9.4.2.1.1.11.49.2
error49-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error49 2 }

-- 1.3.6.1.4.1.11.2.3.9.4.2.1.1.11.49.3
error49-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error49 3 }

-- 1.3.6.1.4.1.11.2.3.9.4.2.1.1.11.5.1
error5-time-stamp  OBJECT-TYPE
   SYNTAX      integer
   ACCESS      read-only
   STATUS      optional
   DESCRIPTION "Contains some sort of time stamp indicating when error 5occurred. Example time stamps include the actual time the erroroccurred (in seconds since Jan. 1, 1970), and the total enginepage count. The device POS documents the meaning of the timestamp. "
   USE ""
   INTERACTION " None. "
   OPERATION " Not destructive."
::= { error5 1 }

-- 1.3.6.1.4.1.11.2.3.9.4.2.1.1.11.5.2
error5-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error5 2 }

-- 1.3.6.1.4.1.11.2.3.9.4.2.1.1.11.5.3
error5-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error5 3 }

-- 1.3.6.1.4.1.11.2.3.9.4.2.1.1.11.50.1
error50-time-stamp  OBJECT-TYPE
   SYNTAX      integer
   ACCESS      read-only
   STATUS      optional
   DESCRIPTION "Contains some sort of time stamp indicating when error 50occurred. Example time stamps include the actual time the erroroccurred (in seconds since Jan. 1, 1970), and the total enginepage count. The device POS documents the meaning of the timestamp. "
   USE ""
   INTERACTION " None. "
   OPERATION " Not destructive."
::= { error50 1 }

-- 1.3.6.1.4.1.11.2.3.9.4.2.1.1.11.50.2
error50-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error50 2 }

-- 1.3.6.1.4.1.11.2.3.9.4.2.1.1.11.50.3
error50-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error50 3 }

-- 1.3.6.1.4.1.11.2.3.9.4.2.1.1.11.6.1
error6-time-stamp  OBJECT-TYPE
   SYNTAX      integer
   ACCESS      read-only
   STATUS      optional
   DESCRIPTION "Contains some sort of time stamp indicating when error 6occurred. Example time stamps include the actual time the erroroccurred (in seconds since Jan. 1, 1970), and the total enginepage count. The device POS documents the meaning of the timestamp. "
   USE ""
   INTERACTION " None. "
   OPERATION " Not destructive."
::= { error6 1 }

-- 1.3.6.1.4.1.11.2.3.9.4.2.1.1.11.6.2
error6-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error6 2 }

-- 1.3.6.1.4.1.11.2.3.9.4.2.1.1.11.6.3
error6-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error6 3 }

-- 1.3.6.1.4.1.11.2.3.9.4.2.1.1.11.7.1
error7-time-stamp  OBJECT-TYPE
   SYNTAX      integer
   ACCESS      read-only
   STATUS      optional
   DESCRIPTION "Contains some sort of time stamp indicating when error 7occurred. Example time stamps include the actual time the erroroccurred (in seconds since Jan. 1, 1970), and the total enginepage count. The device POS documents the meaning of the timestamp. "
   USE ""
   INTERACTION " None. "
   OPERATION " Not destructive."
::= { error7 1 }

-- 1.3.6.1.4.1.11.2.3.9.4.2.1.1.11.7.2
error7-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error7 2 }

-- 1.3.6.1.4.1.11.2.3.9.4.2.1.1.11.7.3
error7-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error7 3 }

-- 1.3.6.1.4.1.11.2.3.9.4.2.1.1.11.8.1
error8-time-stamp  OBJECT-TYPE
   SYNTAX      integer
   ACCESS      read-only
   STATUS      optional
   DESCRIPTION "Contains some sort of time stamp indicating when error 8occurred. Example time stamps include the actual time the erroroccurred (in seconds since Jan. 1, 1970), and the total enginepage count. The device POS documents the meaning of the timestamp. "
   USE ""
   INTERACTION " None. "
   OPERATION " Not destructive."
::= { error8 1 }

-- 1.3.6.1.4.1.11.2.3.9.4.2.1.1.11.8.2
error8-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error8 2 }

-- 1.3.6.1.4.1.11.2.3.9.4.2.1.1.11.8.3
error8-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error8 3 }

-- 1.3.6.1.4.1.11.2.3.9.4.2.1.1.11.9.1
error9-time-stamp  OBJECT-TYPE
   SYNTAX      integer
   ACCESS      read-only
   STATUS      optional
   DESCRIPTION "Contains some sort of time stamp indicating when error 9occurred. Example time stamps include the actual time the erroroccurred (in seconds since Jan. 1, 1970), and the total enginepage count. The device POS documents the meaning of the timestamp. "
   USE ""
   INTERACTION " None. "
   OPERATION " Not destructive."
::= { error9 1 }

-- 1.3.6.1.4.1.11.2.3.9.4.2.1.1.11.9.2
error9-code  OBJECT-TYPE
   SYNTAX      integer
   ACCESS      read-only
   STATUS      optional
   DESCRIPTION "Contains a device specific error code. Each device POS shouldlist what errors are logged to the error log and the meaning ofeach supported error code value. "
   USE ""
   INTERACTION " None. "
   OPERATION " Not destructive."
::= { error9 2 }

-- 1.3.6.1.4.1.11.2.3.9.4.2.1.1.11.9.3
error9-date-time  OBJECT-TYPE
   SYNTAX      binary
   ACCESS      read-only
   STATUS      optional
   DESCRIPTION "This item contains the date and the time at which an erroroccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { error9 3 }

-- 1.3.6.1.4.1.11.2.3.9.4.2.1.1.16.1.1.1
printed-media-simplex-count  OBJECT-TYPE
   SYNTAX      integer
   ACCESS      read-only
   STATUS      optional
   DESCRIPTION "Total number of simplex pages printed in this media size. "
   USE ""
   INTERACTION "  "
   OPERATION " Not destructive."
::= { printed-media-usage 1 }

-- 1.3.6.1.4.1.11.2.3.9.4.2.1.1.16.1.1.10
printed-media-dimplex-count  OBJECT-TYPE
   SYNTAX      integer
   ACCESS      read-only
   STATUS      optional
   DESCRIPTION "Total number of mono dimplex pages printed in this media size.A dimplex page is one that has been printed in duplex mode butthe back side is blank. Dimplex pages occur when the printerfirmware inserts a blank page in order to complete a duplexedjob which is sent to the printer with an odd number of pages. "
   USE ""
   INTERACTION "  "
   OPERATION " Not destructive."
::= { printed-media-usage 10 }

-- 1.3.6.1.4.1.11.2.3.9.4.2.1.1.16.1.1.11
printed-media-combined-simplex-count  OBJECT-TYPE
   SYNTAX      integer
   ACCESS      read-only
   STATUS      optional
   DESCRIPTION "Total number of simplex pages printed on this media size. "
   USE ""
   INTERACTION "  "
   OPERATION " Not destructive."
::= { printed-media-usage 11 }

-- 1.3.6.1.4.1.11.2.3.9.4.2.1.1.16.1.1.12
printed-media-combined-duplex-count  OBJECT-TYPE
   SYNTAX      integer
   ACCESS      read-only
   STATUS      optional
   DESCRIPTION "Total number of duplex pages printed on this media size. "
   USE ""
   INTERACTION "  "
   OPERATION " Not destructive."
::= { printed-media-usage 12 }

-- 1.3.6.1.4.1.11.2.3.9.4.2.1.1.16.1.1.13
printed-media-combined-simplex-total  OBJECT-TYPE
   SYNTAX      integer
   ACCESS      read-only
   STATUS      optional
   DESCRIPTION "Total number of simplex pages printed on this device. "
   USE ""
   INTERACTION "  "
   OPERATION " Not destructive."
::= { printed-media-usage 13 }

-- 1.3.6.1.4.1.11.2.3.9.4.2.1.1.16.1.1.14
printed-media-combined-duplex-total  OBJECT-TYPE
   SYNTAX      integer
   ACCESS      read-only
   STATUS      optional
   DESCRIPTION "Total number of duplex pages printed on this device. "
   USE ""
   INTERACTION "  "
   OPERATION " Not destructive."
::= { printed-media-usage 14 }

-- 1.3.6.1.4.1.11.2.3.9.4.2.1.1.16.1.1.15
impression-based-duplex-count-supported  OBJECT-TYPE
   SYNTAX      enumerated { eFalse (1) , eTrue (2) }
   ACCESS      read-only
   STATUS      optional
   DESCRIPTION "The object is used to get the information on new duplexcounting mechanism. With this new mechanism the Duplex countwould represent actual Duplex count and not half of the count.eTrue means feature is available for the user "
   USE ""
   INTERACTION " None. "
   OPERATION " Accessing this object identifier is NOT destructive in anymanner."
::= { printed-media-usage 15 }

-- 1.3.6.1.4.1.11.2.3.9.4.2.1.1.16.1.1.2
printed-media-simplex-charge  OBJECT-TYPE
   SYNTAX      real
   ACCESS      read-write
   STATUS      optional
   DESCRIPTION "Charge for each simplex page printed in this media size. "
   USE ""
   INTERACTION "  "
   OPERATION " Not destructive."
::= { printed-media-usage 2 }

-- 1.3.6.1.4.1.11.2.3.9.4.2.1.1.16.1.1.3
printed-media-duplex-count  OBJECT-TYPE
   SYNTAX      integer
   ACCESS      read-only
   STATUS      optional
   DESCRIPTION "Total number of duplex pages printed in this media size. "
   USE ""
   INTERACTION "  "
   OPERATION " Not destructive."
::= { printed-media-usage 3 }

-- 1.3.6.1.4.1.11.2.3.9.4.2.1.1.16.1.1.4
printed-media-duplex-charge  OBJECT-TYPE
   SYNTAX      real
   ACCESS      read-write
   STATUS      optional
   DESCRIPTION "Charge for each duplex page printed in this media size. "
   USE ""
   INTERACTION "  "
   OPERATION " Not destructive."
::= { printed-media-usage 4 }

-- 1.3.6.1.4.1.11.2.3.9.4.2.1.1.16.1.1.5
printed-media-total-charge  OBJECT-TYPE
   SYNTAX      real
   ACCESS      read-only
   STATUS      optional
   DESCRIPTION "The total charge for pages printed in this media size. "
   USE ""
   INTERACTION "  "
   OPERATION " Not destructive."
::= { printed-media-usage 5 }

-- 1.3.6.1.4.1.11.2.3.9.4.2.1.1.16.1.1.7
printed-media-combined-total  OBJECT-TYPE
   SYNTAX      real
   ACCESS      read-write
   STATUS      optional
   DESCRIPTION "Total number of letter equivalently weighted pages both colorand mono combined with this printer. "
   USE ""
   INTERACTION "  "
   OPERATION " Not destructive."
::= { printed-media-usage 7 }

-- 1.3.6.1.4.1.11.2.3.9.4.2.1.1.16.1.10
source-tray-usage-total  OBJECT-TYPE
   SYNTAX      integer
   ACCESS      read-only
   STATUS      optional
   DESCRIPTION "This object reports the total source tray usage for the life ofthe printer. This value is reported on the usage page. "
   USE ""
   INTERACTION "  "
   OPERATION " Not destructive."
::= { printer-accounting 10 }

-- 1.3.6.1.4.1.11.2.3.9.4.2.1.1.16.1.11
destination-bin-usage-total  OBJECT-TYPE
   SYNTAX      integer
   ACCESS      read-only
   STATUS      optional
   DESCRIPTION "This object reports the total destination bin usage for thelife of the printer. This value is reported on the usage page. "
   USE "  "
   INTERACTION "  "
   OPERATION " Not destructive."
::= { printer-accounting 11 }

-- 1.3.6.1.4.1.11.2.3.9.4.2.1.1.16.1.12
usage-printer-mono-total-charge  OBJECT-TYPE
   SYNTAX      real
   ACCESS      read-only
   STATUS      optional
   DESCRIPTION "Total printer charge for all paper sizes printed in monochromeonly. "
   USE ""
   INTERACTION " None. "
   OPERATION " Not destructive."
::= { printer-accounting 12 }

-- 1.3.6.1.4.1.11.2.3.9.4.2.1.1.16.1.13
usage-printer-color-total-charge  OBJECT-TYPE
   SYNTAX      real
   ACCESS      read-only
   STATUS      optional
   DESCRIPTION "Total printer charge for all paper sizes printed in coloronly. "
   USE ""
   INTERACTION " None. "
   OPERATION " Not destructive."
::= { printer-accounting 13 }

-- 1.3.6.1.4.1.11.2.3.9.4.2.1.1.16.1.14.10
print-meter-category-total  OBJECT-TYPE
   SYNTAX      real
   ACCESS      read-only
   STATUS      optional
   DESCRIPTION "Total number of simplex plus duplex pages printed for thiscategory of printed pages. "
   USE ""
   INTERACTION "  "
   OPERATION " Not destructive."
::= { print-meter-usage 10 }

-- 1.3.6.1.4.1.11.2.3.9.4.2.1.1.16.1.14.11
print-meter-dimplex-total  OBJECT-TYPE
   SYNTAX      integer
   ACCESS      read-only
   STATUS      optional
   DESCRIPTION "Total number of dimplex pages printed for this category ofprinted pages. "
   USE ""
   INTERACTION "  "
   OPERATION " Not destructive."
::= { print-meter-usage 11 }

-- 1.3.6.1.4.1.11.2.3.9.4.2.1.1.16.1.14.2
print-meter-usage-threshold  OBJECT-TYPE
   SYNTAX      integer
   ACCESS      read-only
   STATUS      optional
   DESCRIPTION "A value indicating the threshold value for this category ofpages. The device POS will indicate the units of measure forthis threshold value. "
   USE ""
   INTERACTION "  "
   OPERATION " Not destructive."
::= { print-meter-usage 2 }

-- 1.3.6.1.4.1.11.2.3.9.4.2.1.1.16.1.14.3
print-meter-print-quality  OBJECT-TYPE
   SYNTAX      enumerated { ePrintQualityMono (1) , ePrintQualityGood (2) , ePrintQualityBest (3) }
   ACCESS      read-only
   STATUS      optional
   DESCRIPTION "This enumeration describes the selected print quality for thiscategory of printed pages. "
   USE ""
   INTERACTION "  "
   OPERATION " Not destructive."
::= { print-meter-usage 3 }

-- 1.3.6.1.4.1.11.2.3.9.4.2.1.1.16.1.14.4
print-meter-simplex-count  OBJECT-TYPE
   SYNTAX      integer
   ACCESS      read-only
   STATUS      optional
   DESCRIPTION "Total number of simplex pages printed for this category ofprinted pages. "
   USE ""
   INTERACTION "  "
   OPERATION " Not destructive."
::= { print-meter-usage 4 }

-- 1.3.6.1.4.1.11.2.3.9.4.2.1.1.16.1.14.5
print-meter-duplex-count  OBJECT-TYPE
   SYNTAX      integer
   ACCESS      read-only
   STATUS      optional
   DESCRIPTION "Total number of duplex pages printed for this category ofprinted pages. "
   USE ""
   INTERACTION "  "
   OPERATION " Not destructive."
::= { print-meter-usage 5 }

-- 1.3.6.1.4.1.11.2.3.9.4.2.1.1.16.1.14.6
print-meter-total-charge  OBJECT-TYPE
   SYNTAX      real
   ACCESS      read-only
   STATUS      optional
   DESCRIPTION "Total number of simplex plus duplex pages printed multiplied bythe unit charge for each given media size for this category ofprinted pages. "
   USE ""
   INTERACTION "  "
   OPERATION " Not destructive."
::= { print-meter-usage 6 }

-- 1.3.6.1.4.1.11.2.3.9.4.2.1.1.16.1.14.7
print-meter-dimplex-count  OBJECT-TYPE
   SYNTAX      integer
   ACCESS      read-only
   STATUS      optional
   DESCRIPTION "Total number of dimplex pages printed for this category ofprinted pages. "
   USE ""
   INTERACTION "  "
   OPERATION " Not destructive."
::= { print-meter-usage 7 }

-- 1.3.6.1.4.1.11.2.3.9.4.2.1.1.16.1.14.8
print-meter-simplex-total  OBJECT-TYPE
   SYNTAX      integer
   ACCESS      read-only
   STATUS      optional
   DESCRIPTION "Total number of simplex pages printed for this category ofprinted pages. "
   USE ""
   INTERACTION "  "
   OPERATION " Not destructive."
::= { print-meter-usage 8 }

-- 1.3.6.1.4.1.11.2.3.9.4.2.1.1.16.1.14.9
print-meter-duplex-total  OBJECT-TYPE
   SYNTAX      integer
   ACCESS      read-only
   STATUS      optional
   DESCRIPTION "Total number of duplex pages printed for this category ofprinted pages. "
   USE ""
   INTERACTION "  "
   OPERATION " Not destructive."
::= { print-meter-usage 9 }

-- 1.3.6.1.4.1.11.2.3.9.4.2.1.1.16.1.15
usage-printer-mono-simplex-total  OBJECT-TYPE
   SYNTAX      integer
   ACCESS      read-only
   STATUS      optional
   DESCRIPTION "This object reports the total of monochrome simplex pagesprinted on this device. This value is the sum of allPRINTED-MEDIA-SIMPLEX-COUNT.n counter values. "
   USE ""
   INTERACTION "  "
   OPERATION " Not destructive."
::= { printer-accounting 15 }

-- 1.3.6.1.4.1.11.2.3.9.4.2.1.1.16.1.16
usage-printer-mono-duplex-total  OBJECT-TYPE
   SYNTAX      integer
   ACCESS      read-only
   STATUS      optional
   DESCRIPTION "This object reports the total of monochrome duplex pagesprinted on this device. This value is the sum of allPRINTED-MEDIA-DUPLEX-COUNT.n counter values. "
   USE ""
   INTERACTION "  "
   OPERATION " Not destructive."
::= { printer-accounting 16 }

-- 1.3.6.1.4.1.11.2.3.9.4.2.1.1.16.1.17
usage-printer-mono-dimplex-total  OBJECT-TYPE
   SYNTAX      integer
   ACCESS      read-only
   STATUS      optional
   DESCRIPTION "This object reports the total of monochrome dimplex pagesprinted on this device. This value is the sum of allPRINTED-MEDIA-DIMPLEX-COUNT.n counter values. "
   USE ""
   INTERACTION "  "
   OPERATION " Not destructive."
::= { printer-accounting 17 }

-- 1.3.6.1.4.1.11.2.3.9.4.2.1.1.16.1.2
usage-printer-total-charge  OBJECT-TYPE
   SYNTAX      real
   ACCESS      read-only
   STATUS      optional
   DESCRIPTION "Total printer charge for all paper sizes printed. "
   USE ""
   INTERACTION "  "
   OPERATION " Not destructive."
::= { printer-accounting 2 }

-- 1.3.6.1.4.1.11.2.3.9.4.2.1.1.16.1.5
usage-instructions-line1  OBJECT-TYPE
   SYNTAX      string
   ACCESS      read-write
   STATUS      optional
   DESCRIPTION "The first line of usage instructions for the deviceuser.Appears on Line 1 of the usage page. "
   USE ""
   INTERACTION "  "
   OPERATION " Not destructive."
::= { printer-accounting 5 }

-- 1.3.6.1.4.1.11.2.3.9.4.2.1.1.16.1.6
usage-instructions-line2  OBJECT-TYPE
   SYNTAX      string
   ACCESS      read-write
   STATUS      optional
   DESCRIPTION "The second line of usage instructions for the deviceuser.Appears on Line 1 of the usage page. "
   USE ""
   INTERACTION "  "
   OPERATION " Not destructive."
::= { printer-accounting 6 }

-- 1.3.6.1.4.1.11.2.3.9.4.2.1.1.16.1.7
usage-instructions-line3  OBJECT-TYPE
   SYNTAX      string
   ACCESS      read-write
   STATUS      optional
   DESCRIPTION "The third line of usage instructions for the deviceuser.Appears on Line 1 of the usage page. "
   USE ""
   INTERACTION "  "
   OPERATION " Not destructive."
::= { printer-accounting 7 }

-- 1.3.6.1.4.1.11.2.3.9.4.2.1.1.16.1.8
usage-instructions-line4  OBJECT-TYPE
   SYNTAX      string
   ACCESS      read-write
   STATUS      optional
   DESCRIPTION "The fourth line of usage instructions for the deviceuser.Appears on Line 1 of the usage page. "
   USE ""
   INTERACTION "  "
   OPERATION " Not destructive."
::= { printer-accounting 8 }

-- 1.3.6.1.4.1.11.2.3.9.4.2.1.1.16.1.9
printed-modes-usage-total  OBJECT-TYPE
   SYNTAX      integer
   ACCESS      read-only
   STATUS      optional
   DESCRIPTION " This object reports the total color and mono print modes usagefor the life of the printer. This value is reported on theusage page. "
   USE ""
   INTERACTION "  "
   OPERATION " Not destructive."
::= { printer-accounting 9 }

-- 1.3.6.1.4.1.11.2.3.9.4.2.1.1.16.3.1.1
printed-media-color-simplex-count  OBJECT-TYPE
   SYNTAX      integer
   ACCESS      read-only
   STATUS      optional
   DESCRIPTION "Total number of color simplex pages printed in this mediasize. "
   USE ""
   INTERACTION "  "
   OPERATION " Not destructive."
::= { printed-media-color-usage 1 }

-- 1.3.6.1.4.1.11.2.3.9.4.2.1.1.16.3.1.3
printed-media-color-duplex-count  OBJECT-TYPE
   SYNTAX      integer
   ACCESS      read-only
   STATUS      optional
   DESCRIPTION "Total number of color duplex pages printed in this media size. "
   USE "  "
   INTERACTION "  "
   OPERATION " Not destructive."
::= { printed-media-color-usage 3 }

-- 1.3.6.1.4.1.11.2.3.9.4.2.1.1.16.3.1.5
printed-media-color-total-count  OBJECT-TYPE
   SYNTAX      real
   ACCESS      read-only
   STATUS      optional
   DESCRIPTION "The total count for color pages printed in this media size. "
   USE ""
   INTERACTION "  "
   OPERATION " Not destructive."
::= { printed-media-color-usage 5 }

-- 1.3.6.1.4.1.11.2.3.9.4.2.1.1.16.3.1.6
printed-media-color-dimplex-count  OBJECT-TYPE
   SYNTAX      integer
   ACCESS      read-only
   STATUS      optional
   DESCRIPTION "Total number of color dimplex pages printed in this media size.A color dimplex page is a color page that has been printed induplex mode but the back side is blank. Dimplex pages occurwhen the printer firmware inserts a blank page in order tocomplete a duplexed job which is sent to the printer with anodd number of pages. "
   USE ""
   INTERACTION "  "
   OPERATION " Not destructive."
::= { printed-media-color-usage 6 }

-- 1.3.6.1.4.1.11.2.3.9.4.2.1.1.16.4.1.1
printed-modes-mono-count  OBJECT-TYPE
   SYNTAX      integer
   ACCESS      read-only
   STATUS      optional
   DESCRIPTION "Total number of mono pages printed in this fuser mode. "
   USE ""
   INTERACTION "  "
   OPERATION " Not destructive."
::= { printed-modes-usage 1 }

-- 1.3.6.1.4.1.11.2.3.9.4.2.1.1.16.4.1.3
printed-modes-color-count  OBJECT-TYPE
   SYNTAX      integer
   ACCESS      read-only
   STATUS      optional
   DESCRIPTION "Total number of color pages printed in this fuser mode. "
   USE ""
   INTERACTION "  "
   OPERATION " Not destructive."
::= { printed-modes-usage 3 }

-- 1.3.6.1.4.1.11.2.3.9.4.2.1.1.16.4.1.5
printed-modes-total-count  OBJECT-TYPE
   SYNTAX      integer
   ACCESS      read-only
   STATUS      optional
   DESCRIPTION "The total count for pages printed in this fuser mode. "
   USE ""
   INTERACTION "  "
   OPERATION " Not destructive."
::= { printed-modes-usage 5 }

-- 1.3.6.1.4.1.11.2.3.9.4.2.1.1.16.5.1.1
source-tray-usage-count  OBJECT-TYPE
   SYNTAX      integer
   ACCESS      read-only
   STATUS      optional
   DESCRIPTION "Total number of pages printed from this source tray. "
   USE ""
   INTERACTION "  "
   OPERATION " Not destructive."
::= { source-tray-usage 1 }

-- 1.3.6.1.4.1.11.2.3.9.4.2.1.1.16.6.1.1
destination-bin-usage-count  OBJECT-TYPE
   SYNTAX      integer
   ACCESS      read-only
   STATUS      optional
   DESCRIPTION "Total number of pages printed to this destination bin. "
   USE ""
   INTERACTION "  "
   OPERATION " Not destructive."
::= { destination-bin-usage 1 }

-- 1.3.6.1.4.1.11.2.3.9.4.2.1.1.2.100
automatic-daylight-savings  OBJECT-TYPE
   SYNTAX      enumerated { eOff (1) , eOn (2) }
   ACCESS      read-write
   STATUS      optional
   DESCRIPTION "Determines whether or not the automatic adjustment for daylightsavings time is enabled. If it's enabled the device local timewill be automatically adjusted for DST period. "
   USE ""
   INTERACTION " SVM_AUTOMATIC_DAYLIGHT_SAVINGS, DATE-AND-TIME (the device localtime will be affected). "
   OPERATION " Not destructive."
::= { status-system 100 }

-- 1.3.6.1.4.1.11.2.3.9.4.2.1.1.2.101
daylight-savings-start  OBJECT-TYPE
   SYNTAX      binary
   ACCESS      read-write
   STATUS      optional
   DESCRIPTION "A C structure containing the following fields: \\typedef struct { \\ubyte hour; /* hour: 0 to 23 */ \\ubyte weekday; /* weekday: 0(Sunday) to 6 */ \\ubyte occurrence; /* occurrence in the month: 1 to 5 */ \\ubyte month; /* month: 1 to 12 */ \\} dst; \\where ubyte is an unsigned byte (0-255). "
   USE ""
   INTERACTION " SVM_DAYLIGHT_SAVINGS_START, DATE-AND-TIME (the device localtime will be affected). "
   OPERATION " Not destructive."
::= { status-system 101 }

-- 1.3.6.1.4.1.11.2.3.9.4.2.1.1.2.102
daylight-savings-end  OBJECT-TYPE
   SYNTAX      binary
   ACCESS      read-write
   STATUS      optional
   DESCRIPTION "A C structure containing the following fields: \\typedef struct { \\ubyte hour; /* hour: 0 to 23 */ \\ubyte weekday; /* weekday: 0(Sunday) to 6 */ \\ubyte occurrence; /* occurrence in the month: 1 to 5 */ \\ubyte month; /* month: 1 to 12 */ \\} dst; \\where ubyte is an unsigned byte (0-255). "
   USE ""
   INTERACTION " SVM_DAYLIGHT_SAVINGS_END, DATE-AND-TIME (the device local timewill be affected) "
   OPERATION " Not destructive."
::= { status-system 102 }

-- 1.3.6.1.4.1.11.2.3.9.4.2.1.1.2.103
daylight-savings-offset  OBJECT-TYPE
   SYNTAX      integer
   ACCESS      read-write
   STATUS      optional
   DESCRIPTION "Controls the offset in minutes to be added to the time when DSTis in effect. "
   USE ""
   INTERACTION " SVM_DAYLIGHT_SAVINGS_OFFSET, DATE-AND-TIME (the device localtime will be affected). "
   OPERATION " Not destructive."
::= { status-system 103 }

-- 1.3.6.1.4.1.11.2.3.9.4.2.1.1.2.104
daylight-savings-reset  OBJECT-TYPE
   SYNTAX      enumerated { eResetToDefault (1) , eCustomized (2) }
   ACCESS      read-write
   STATUS      optional
   DESCRIPTION "This object is used to reset (set back to factory default forthe current time zone) or read the current status of the DSTsettings. When Set to eResetToDefault, this object can be usedto reset all the DST related objects back to their factorydefault values. Setting this object with an enumerated value ofeCustomized has no effect. When a Get operation is performed onthis object it will return a value eResetToDefault if all DSTsettings are still set to they factory value. It will returneCustomized if any DST parameter has been set to a customvalue. "
   USE ""
   INTERACTION " SVM_AUTOMATIC_DAYLIGHT_SAVINGS and AUTOMATIC-DAYLIGHT-SAVINGS;SVM_DAYLIGHT_SAVINGS_START and DAYLIGHT-SAVINGS-START;SVM_DAYLIGHT_SAVINGS_END and DAYLIGHT-SAVINGS-END;SVM_DAYLIGHT_SAVINGS_OFFSET and DAYLIGHT-SAVINGS-OFFSET;DATE-AND-TIME (the device local time will be affected) "
   OPERATION " Not destructive."
::= { status-system 104 }

-- 1.3.6.1.4.1.11.2.3.9.4.2.1.1.2.105
warning-log-clear  OBJECT-TYPE
   SYNTAX      enumerated { eClearErrorLog (1) }
   ACCESS      write-only
   STATUS      optional
   DESCRIPTION "Setting this object clears all the entries in the warning logsub-tree. "
   USE ""
   INTERACTION " When successfully set, clears all the entries in the warninglog sub-tree. "
   OPERATION " Not destructive."
::= { status-system 105 }

-- 1.3.6.1.4.1.11.2.3.9.4.2.1.1.2.17
date-and-time  OBJECT-TYPE
   SYNTAX      binary
   ACCESS      read-write , trappable
   STATUS      optional
   DESCRIPTION "A C structure containing the following fields: \\ typedefstruct { \\ubyte yr; /* year: 0 to 99 */ \\ubyte mon; /* month: 1 to 12 */ \\ubyte day; /* day: 1 to 31 */ \\ubyte wday; /* Day of week: 1 to 07 */ \\ubyte hr; /* hour: 0 to 23 */ \\ubyte min; /* minute: 0 to 59 */ \\ubyte sec; /* second: 0 to 59 */ \\} date_t; \\where ubyte is an unsigned byte (0-255). "
   USE ""
   INTERACTION " This has no interaction with any other object. "
   OPERATION " Accessing this OI affects scheduled faxes."
::= { status-system 17 }

-- 1.3.6.1.4.1.11.2.3.9.4.2.1.1.2.19
service-id  OBJECT-TYPE
   SYNTAX      string
   ACCESS      read-write
   STATUS      optional
   DESCRIPTION "A read of this object will return the current SERVICE ID valuein the printer. The format is 'YYDDD' where: \\YY = calendar year - 1990 \\DDD = (calendar month - 1) * 30 + (calendar day of themonth or 30, if &gt; 30) \\A write of this object will only succeed if theMANUFACTURING-CONTROL PML object has been set with the correct<<hidden>>. If the write operation is not allowed, this objectwill return an &lt;ErrorActionCanNotBePerformedNow&gt; status. "
   USE ""
   INTERACTION " Changing the value of this object may change the value of theINSTALL-DATE PML object. "
   OPERATION " Not destructive."
::= { status-system 19 }

-- 1.3.6.1.4.1.11.2.3.9.4.2.1.1.2.20.1.3
show-address  OBJECT-TYPE
   SYNTAX      enumerated { eAuto (3) , eOff (1) }
   ACCESS      read-write
   STATUS      optional
   DESCRIPTION "If this object is set to eAuto, and the device has an IPaddress, the IP address of the device will be shown with theREADY message. If this object is set to eOff, the IP addresswill not be shown. "
   USE ""
   INTERACTION " If more than one network card is installed, only the address ofthe card in the first position will be displayed. "
   OPERATION " Not destructive."
::= { display-status 3 }

-- 1.3.6.1.4.1.11.2.3.9.4.2.1.1.2.28
time-display  OBJECT-TYPE
   SYNTAX      enumerated { eTimeDisplayTwelveHour (1) , eTimeDisplayTwentyFourHour (2) }
   ACCESS      read-write , trappable
   STATUS      optional
   DESCRIPTION "Controls front-panel time display format. Set toeTimeDisplayTwelveHour for AM/PM display. Set toeTimeDisplayTwentyFourHour for military-type display. "
   USE ""
   INTERACTION " TBD. "
   OPERATION " Not destructive."
::= { status-system 28 }

-- 1.3.6.1.4.1.11.2.3.9.4.2.1.1.2.35
job-input-auto-continue-timeout  OBJECT-TYPE
   SYNTAX      integer
   ACCESS      read-write
   STATUS      optional
   DESCRIPTION "The number of seconds the device waits after a job relatedcontinuable error occurs before automatically continuing. Anexample job related continuable error is the job requesting amedia size that is not available. After the timeout expires,the device will continue processing the job as if a continueevent occurred, such as the front panel continue key beingpressed. If the value is -1, the device does not automaticallycontinue after a job related continuable error occurs. If thevalue is 0, the device immediately continues. If the value isgreater than 0, the value represents the timeout value inseconds. "
   USE ""
   INTERACTION " None. "
   OPERATION " Not destructive."
::= { status-system 35 }

-- 1.3.6.1.4.1.11.2.3.9.4.2.1.1.2.36
job-input-auto-continue-mode  OBJECT-TYPE
   SYNTAX      collection { cCancelJob (0) , cAutoMediaSizeOverride (1) , cAutoMediaNameOverride (2) , cUSMediaSizeOverride (3) , cISOMediaSizeOverride (4) }
   ACCESS      read-write
   STATUS      optional
   DESCRIPTION "Returns or sets the device behavior when the desired media isnot currently available. \\cCancelJob - The device cancels the job. The device POSshould explain what happens if this item is not theonly item in the collection. \\cAutoMediaSizeOverride - The device is allowed tosubstitute a different size media. \\cAutoMediaNameOverride - The device is allowed tosubstitute a different media name. \\cUSMediaSizeOverride - The device is allowed to substituteUS media sizes (letter, etc.) for ISO media sizes (A4,etc.). \\cISOMediaSizeOverride - The device is allowed to substituteISO media sizes (A4, etc.) for US media sizes (letter,etc.). \\ "
   USE ""
   INTERACTION "  None. "
   OPERATION " Not destructive."
::= { status-system 36 }

-- 1.3.6.1.4.1.11.2.3.9.4.2.1.1.2.37.1.1
background-status-msg-line1-part1  OBJECT-TYPE
   SYNTAX      string
   ACCESS      read-write
   STATUS      optional
   DESCRIPTION "The string displayed on the device's front panel in place ofthe printer's built-in background status string. An examplebuilt-in background status string is '00 READY'. "
   USE ""
   INTERACTION " None. "
   OPERATION " Not destructive."
::= { background-message1 1 }

-- 1.3.6.1.4.1.11.2.3.9.4.2.1.1.2.37.2.1
background-status-msg-line2-part1  OBJECT-TYPE
   SYNTAX      string
   ACCESS      read-write
   STATUS      optional
   DESCRIPTION "The string displayed on the device's front panel in place ofthe printer's built-in background status string. An examplebuilt-in background status string is '00 READY'. "
   USE ""
   INTERACTION " None. "
   OPERATION " Not destructive."
::= { background-message2 1 }

-- 1.3.6.1.4.1.11.2.3.9.4.2.1.1.2.38
error-log-clear  OBJECT-TYPE
   SYNTAX      enumerated { eClearErrorLog (1) }
   ACCESS      write-only
   STATUS      optional
   DESCRIPTION "Setting this object clears all the entries in the error logsub-tree. "
   USE ""
   INTERACTION " When successfully set, clears all the entries in the error logsub-tree. "
   OPERATION " Not destructive."
::= { status-system 38 }

-- 1.3.6.1.4.1.11.2.3.9.4.2.1.1.2.40
job-output-auto-continue-timeout  OBJECT-TYPE
   SYNTAX      integer (-1..32767)
   ACCESS      read-write
   STATUS      optional
   DESCRIPTION "Returns or sets the time that the printer will wait after anoutput bin becomes full and the printer is trying to deliver asheet of media to that output bin. When the timeout expires,the job is processed according to the OUTBINn-OVERRIDE-MODE. Avalue of -1 indicates that the printer will wait for a continueevent. A non-negative value is the number of seconds to wait. "
   USE ""
   INTERACTION " None. "
   OPERATION " Not destructive."
::= { status-system 40 }

-- 1.3.6.1.4.1.11.2.3.9.4.2.1.1.2.42
collated-originals-support  OBJECT-TYPE
   SYNTAX      collection { cCollatedOriginals (0) , cProofAndHold (1) , cSecurityPrint (2) , cAutoHighlight (3) , cCollatedAtSpeed (4) }
   ACCESS      read-only
   STATUS      optional
   DESCRIPTION "Indicates that the printer can create multiple, collated'originals' of a job and shows the level of support for thiscapability. \\cCollatedOriginals - The printer can create multiplecollated originals, or 'mopies'. This is the basefunctionality required by the other collection items.\\cProofAndHold - The printer saves a copy of the job whileprinting the first mopy. Later, this held job can bereleased and the rest of the mopies will print. \\cSecurityPrint - The printer spools the job and holds thejob until the user releases the job by entering a<<hidden>> at the printer's control panel. \\cAutoHighlight - The printer prints the job a number oftimes with a mail distribution list prepended to eachjob. A different mailing address is highlighted on eachmopy. \\cCollatedAtSpeed - The printer can create multiple collatedcopies where all copies after the original are printedat engine speed. \\ "
   USE ""
   INTERACTION " None. "
   OPERATION " Not destructive."
::= { status-system 42 }

-- 1.3.6.1.4.1.11.2.3.9.4.2.1.1.2.5
on-off-line  OBJECT-TYPE
   SYNTAX      enumerated { eOnline (1) , eOffline (2) , eOfflineAtEndOfJob (3) }
   ACCESS      read-write
   STATUS      optional
   DESCRIPTION "To bring the PDL processing sub-system on or off line. If thedevice is a printer, then the printer does not process printjob data when the printer is off line. PML communicationpersists. "
   USE ""
   INTERACTION " If successful, changes NOT-READY-PRINTER to indicate the PDLprocessing sub-system is not ready, and changes theNOT-READY-PROCESSING-PDL to indicate the PDL processingsub-system is off-line. "
   OPERATION " Not destructive. Trap on the NOT-READY-PROCESSING-PDL object tomonitor changes in on line / off line state."
::= { status-system 5 }

-- 1.3.6.1.4.1.11.2.3.9.4.2.1.1.2.52
localization-languages-supported  OBJECT-TYPE
   SYNTAX      string
   ACCESS      read-only
   STATUS      optional
   DESCRIPTION "The list of languages supported by the device. The languagesare primarily, but not limited to, two character codes from ISO639, each separated by a comma character. "
   USE ""
   INTERACTION " If the Standard Printer MIB object prtLocalizationLanguage issupported, this object contains the combined values of alllocalizations and the order of values is identical. "
   OPERATION " Not destructive."
::= { status-system 52 }

-- 1.3.6.1.4.1.11.2.3.9.4.2.1.1.2.53
localization-countries-supported  OBJECT-TYPE
   SYNTAX      string
   ACCESS      read-only
   STATUS      optional
   DESCRIPTION "The list of countries supported by the device. The countriesare primarily, but not limited to, two character codes from ISO3166, each separated by a comma character. "
   USE ""
   INTERACTION " If the Standard Printer MIB object prtLocalizationCountry issupported, this object contains the combined values of alllocalizations and the order of values is identical. "
   OPERATION " Not destructive."
::= { status-system 53 }

-- 1.3.6.1.4.1.11.2.3.9.4.2.1.1.2.59
host-application-available-memory  OBJECT-TYPE
   SYNTAX      integer
   ACCESS      read-only
   STATUS      optional
   DESCRIPTION "Returns the amount of memory, in bytes, that the device hasavailable for job-related processing or resources. Also knownas driver work space (DWS) memory. "
   USE ""
   INTERACTION " None. "
   OPERATION " Not destructive."
::= { status-system 59 }

-- 1.3.6.1.4.1.11.2.3.9.4.2.1.1.2.7
auto-continue  OBJECT-TYPE
   SYNTAX      enumerated { eOff (1) , eOn (2) }
   ACCESS      read-write
   STATUS      optional
   DESCRIPTION "Indicates if the device will automatically continue afterencountering a continuable error. If AUTO-CONTINUE is set toeOn, the device will automatically generate continue event toacknowledge continuable errors. If AUTO-CONTINUE is set toeOff, then some other continue event will have to acknowledgethe continuable error. "
   USE ""
   INTERACTION " May not be settable if NOT-IDLE contains the cProcessingPDLitem. See CONTINUE object for a description of continuableerrors. "
   OPERATION " Not destructive."
::= { status-system 7 }

-- 1.3.6.1.4.1.11.2.3.9.4.2.1.1.2.8
install-date  OBJECT-TYPE
   SYNTAX      string
   ACCESS      read-write
   STATUS      optional
   DESCRIPTION "Identifies the date that the device was installed. The formatof the string is 'YYYYMMDDHHmmZ'. Where: \\YYYY is the year. \\MM is the month (1-12). \\DD is the day (1-31). \\HH is the hour of the day (0-23). \\mm are the minutes (0-59). \\'Z' designates Greenwich Mean Time; if 'Z' not specified,value is local time. \\Device POS must specify the conditions for setting thisobject. "
   USE ""
   INTERACTION " None. "
   OPERATION " Not destructive."
::= { status-system 8 }

-- 1.3.6.1.4.1.11.2.3.9.4.2.1.1.2.99
rtc-time-zone  OBJECT-TYPE
   SYNTAX      enumerated { eTzDateline (1) , eTzSamoa (2) , eTzHawaiian (3) , eTzAlaskan (4) , eTzPacific (5) , eTzUSMountain (6) , eTzMexico2 (7) , eTzMountain (8) , eTzCentralAmerica (9) , eTzCentral (10) , eTzMexico (11) , eTzCanadaCentral (12) , eTzSAPacific (13) , eTzEastern (14) , eTzUSEastern (15) , eTzAtlantic (16) , eTzSAWestern (17) , eTzPacificSA (18) , eTzNewfoundland (19) , eTzESouthAmerica (20) , eTzSAEastern (21) , eTzGreenland (22) , eTzMidAtlantic (23) , eTzAzores (24) , eTzCapeVerde (25) , eTzGreenwich (26) , eTzGMT (27) , eTzWEurope (28) , eTzCentralEurope (29) , eTzRomance (30) , eTzCentralEuropean (31) , eTzWCentralAfrica (32) , eTzGTB (33) , eTzEeurope (34) , eTzEgypt (35) , eTzSouthAfrica (36) , eTzFLE (37) , eTzJerusalem (38) , eTzArabic (39) , eTzArab (40) , eTzRussian (41) , eTzEAfrica (42) , eTzIran (43) , eTzArabian (44) , eTzCaucasus (45) , eTzAfghanistan (46) , eTzEkaterinburg (47) , eTzWestAsia (48) , eTzIndia (49) , eTzNepal (50) , eTzNCentralAsia (51) , eTzCentralAsia (52) , eTzSriLanka (53) , eTzMyanmar (54) , eTzSEAsia (55) , eTzNorthAsia (56) , eTzChina (57) , eTzNorthAsiaEast (58) , eTzMalayPeninsula (59) , eTzWAustralia (60) , eTzTaipei (61) , eTzTokyo (62) , eTzKorea (63) , eTzYakutsk (64) , eTzCenAustralia (65) , eTzAUSCentral (66) , eTzEAustralia (67) , eTzAUSEastern (68) , eTzWestPacific (69) , eTzTasmania (70) , eTzVladivostok (71) , eTzCentralPacific (72) , eTzNewZealand (73) , eTzFiji (74) , eTzTonga (75) }
   ACCESS      read-write , trappable
   STATUS      optional
   DESCRIPTION "Controls the time zone, which can be chosen from a list of timezones similar to the one used by Microsoft Windows operatingsystem: eTzDateline -12:00 International Date Line WesteTzSamoa -11:00 Midway Island, Samoa eTzHawaiian -10:00 HawaiieTzAlaskan -09:00 Alaska eTzPacific -08:00 Pacific Time (US &amp;Canada); Tijuana eTzUSMountain -07:00 Arizona eTzMexico2 -07:00Chihuahua, La Paz, Mazatlan eTzMountain -07:00 Mountain Time(US &amp; Canada) eTzCentralAmerica -06:00 Central AmericaeTzCentral -06:00 Central Time (US &amp; Canada) eTzMexico -06:00Guadalajara, Mexico City, Monterrey eTzCanadaCentral -06:00Saskatchewan eTzSAPacific -05:00 Bogota, Lima, Quito eTzEastern-05:00 Eastern Time (US &amp; Canada) eTz"
   USE "astern -05:00 Indiana(East) eTzAtlantic -04:00 Atlantic Time (Canada) eTzSAWestern-04:00 Caracas, La Paz eTzPacificSA -04:00 SantiagoeTzNewfoundland -03:30 Newfoundland eTzESouthAmerica -03:00Brasilia eTzSAEastern -03:00 Buenos Aires, GeorgetowneTzGreenland -03:00 Greenland eTzMidAtlantic -02:00Mid-Atlantic eTzAzores -01:00 Azores eTzCapeVerde -01:00 CapeVerde Is. eTzGreenwich 00:00 Casablanca, Monrovia eTzGMT 00:00Greenwich Mean Time : Dublin, Edinburgh, Lisbon, LondoneTzWEurope +01:00 Amsterdam, Berlin, Bern, Rome, Stockholm,Vienna eTzCentralEurope +01:00 Belgrade, Bratislava, Budapest,Ljubljana, Prague eTzRomance +01:00 Brussels, Copenhagen,Madrid, Paris eTzCentralEuropean +01:00 Sarajevo, Skopje,Warsaw, Zagreb eTzWCentralAfrica +01:00 West Central AfricaeTzGTB +02:00 Athens, Beirut, Istanbul, Minsk eTzEeurope +02:00Bucharest eTzEgypt +02:00 Cairo eTzSouthAfrica +02:00 Harare,Pretoria eTzFLE +02:00 Helsinki, Kyiv, Riga, Sofia, Tallinn,Vilnius eTzJerusalem +02:00 Jerusalem eTzArabic +03:00 BaghdadeTzArab +03:00 Kuwait, Riyadh eTzRussian +03:00 Moscow, St.Petersburg, Volgograd eTzEAfrica +03:00 Nairobi eTzIran +03:30Tehran eTzArabian +04:00 Abu Dhabi, Muscat eTzCaucasus +04:00Baku, Tbilisi, Yerevan eTzAfghanistan +04:30 KabuleTzEkaterinburg +05:00 Ekaterinburg eTzWestAsia +05:00Islamabad, Karachi, Tashkent eTzIndia +05:30 Chennai, Kolkata,Mumbai, New Delhi eTzNepal +05:45 Kathmandu eTzNCentralAsia+06:00 Almaty, Novosibirsk eTzCentralAsia +06:00 Astana, DhakaeTzSriLanka +06:00 Sri Jayawardenepura eTzMyanmar +06:30Rangoon eTzSEAsia +07:00 Bangkok, Hanoi, Jakarta eTzNorthAsia+07:00 Krasnoyarsk eTzChina +08:00 Beijing, Chongqing, HongKong, Urumqi eTzNorthAsiaEast +08:00 Irkutsk, Ulaan BataareTzMalayPeninsula +08:00 Kuala Lumpur, Singapore eTzWAustralia+08:00 Perth eTzTaipei +08:00 Taipei eTzTokyo +09:00 Osaka,Sapporo, Tokyo eTzKorea +09:00 Seoul eTzYakutsk +09:00 YakutskeTzCenAustralia +09:30 Adelaide eTzAUSCentral +09:30 DarwineTzEAustralia +10:00 Brisbane eTzAUSEastern +10:00 Canberra,Melbourne, Sydney eTzWestPacific +10:00 Guam, Port MoresbyeTzTasmania +10:00 Hobart eTzVladivostok +10:00 VladivostokeTzCentralPacific +11:00 Magadan, Solomon Is., New CaledoniaeTzNewZealand +12:00 Auckland, Wellington eTzFiji +12:00 Fiji,Kamchatka, MarshallIs. eTzTonga +13:00 Nuku'alofa "
   INTERACTION " SVM_RTC_TIME_ZONE, DATE-AND-TIME (the device local time will beaffected), DST start and end time. The SysVarsSVM_DAYLIGHT_SAVINGS_START, SVM_DAYLIGHT_SAVINGS_END andSVM_DAYLIGHT_SAVINGS_OFFSET will be erased. PML objectsDAYLIGHT-SAVINGS-START, DAYLIGHT-SAVINGS-END andDAYLIGHT-SAVINGS-OFFSET may change. "
   OPERATION " Not destructive."
::= { status-system 99 }

-- 1.3.6.1.4.1.11.2.3.9.4.2.1.1.22.1.1
warning1-time-stamp  OBJECT-TYPE
   SYNTAX      integer
   ACCESS      read-only
   STATUS      optional
   DESCRIPTION "Contains some sort of time stamp indicating when warning 1occurred. Example time stamps include the actual time thewarning occurred (in seconds since Jan. 1, 1970), and the totalengine page count. The device POS documents the meaning of thetime stamp. "
   USE ""
   INTERACTION " None. "
   OPERATION " Not destructive."
::= { warning1 1 }

-- 1.3.6.1.4.1.11.2.3.9.4.2.1.1.22.1.2
warning1-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning1 2 }

-- 1.3.6.1.4.1.11.2.3.9.4.2.1.1.22.1.3
warning1-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning1 3 }

-- 1.3.6.1.4.1.11.2.3.9.4.2.1.1.22.10.1
warning10-time-stamp  OBJECT-TYPE
   SYNTAX      integer
   ACCESS      read-only
   STATUS      optional
   DESCRIPTION "Contains some sort of time stamp indicating when warning 10occurred. Example time stamps include the actual time thewarning occurred (in seconds since Jan. 1, 1970), and the totalengine page count. The device POS documents the meaning of thetime stamp. "
   USE ""
   INTERACTION " None. "
   OPERATION " Not destructive."
::= { warning10 1 }

-- 1.3.6.1.4.1.11.2.3.9.4.2.1.1.22.10.2
warning10-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning10 2 }

-- 1.3.6.1.4.1.11.2.3.9.4.2.1.1.22.10.3
warning10-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning10 3 }

-- 1.3.6.1.4.1.11.2.3.9.4.2.1.1.22.11.1
warning11-time-stamp  OBJECT-TYPE
   SYNTAX      integer
   ACCESS      read-only
   STATUS      optional
   DESCRIPTION "Contains some sort of time stamp indicating when warning 11occurred. Example time stamps include the actual time thewarning occurred (in seconds since Jan. 1, 1970), and the totalengine page count. The device POS documents the meaning of thetime stamp. "
   USE ""
   INTERACTION " None. "
   OPERATION " Not destructive."
::= { warning11 1 }

-- 1.3.6.1.4.1.11.2.3.9.4.2.1.1.22.11.2
warning11-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning11 2 }

-- 1.3.6.1.4.1.11.2.3.9.4.2.1.1.22.11.3
warning11-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning11 3 }

-- 1.3.6.1.4.1.11.2.3.9.4.2.1.1.22.12.1
warning12-time-stamp  OBJECT-TYPE
   SYNTAX      integer
   ACCESS      read-only
   STATUS      optional
   DESCRIPTION "Contains some sort of time stamp indicating when warning 12occurred. Example time stamps include the actual time thewarning occurred (in seconds since Jan. 1, 1970), and the totalengine page count. The device POS documents the meaning of thetime stamp. "
   USE ""
   INTERACTION " None. "
   OPERATION " Not destructive."
::= { warning12 1 }

-- 1.3.6.1.4.1.11.2.3.9.4.2.1.1.22.12.2
warning12-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning12 2 }

-- 1.3.6.1.4.1.11.2.3.9.4.2.1.1.22.12.3
warning12-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning12 3 }

-- 1.3.6.1.4.1.11.2.3.9.4.2.1.1.22.13.1
warning13-time-stamp  OBJECT-TYPE
   SYNTAX      integer
   ACCESS      read-only
   STATUS      optional
   DESCRIPTION "Contains some sort of time stamp indicating when warning 13occurred. Example time stamps include the actual time thewarning occurred (in seconds since Jan. 1, 1970), and the totalengine page count. The device POS documents the meaning of thetime stamp. "
   USE ""
   INTERACTION " None. "
   OPERATION " Not destructive."
::= { warning13 1 }

-- 1.3.6.1.4.1.11.2.3.9.4.2.1.1.22.13.2
warning13-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning13 2 }

-- 1.3.6.1.4.1.11.2.3.9.4.2.1.1.22.13.3
warning13-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning13 3 }

-- 1.3.6.1.4.1.11.2.3.9.4.2.1.1.22.14.1
warning14-time-stamp  OBJECT-TYPE
   SYNTAX      integer
   ACCESS      read-only
   STATUS      optional
   DESCRIPTION "Contains some sort of time stamp indicating when warning 14occurred. Example time stamps include the actual time thewarning occurred (in seconds since Jan. 1, 1970), and the totalengine page count. The device POS documents the meaning of thetime stamp. "
   USE ""
   INTERACTION " None. "
   OPERATION " Not destructive."
::= { warning14 1 }

-- 1.3.6.1.4.1.11.2.3.9.4.2.1.1.22.14.2
warning14-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning14 2 }

-- 1.3.6.1.4.1.11.2.3.9.4.2.1.1.22.14.3
warning14-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning14 3 }

-- 1.3.6.1.4.1.11.2.3.9.4.2.1.1.22.15.1
warning15-time-stamp  OBJECT-TYPE
   SYNTAX      integer
   ACCESS      read-only
   STATUS      optional
   DESCRIPTION "Contains some sort of time stamp indicating when warning 15occurred. Example time stamps include the actual time thewarning occurred (in seconds since Jan. 1, 1970), and the totalengine page count. The device POS documents the meaning of thetime stamp. "
   USE ""
   INTERACTION " None. "
   OPERATION " Not destructive."
::= { warning15 1 }

-- 1.3.6.1.4.1.11.2.3.9.4.2.1.1.22.15.2
warning15-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning15 2 }

-- 1.3.6.1.4.1.11.2.3.9.4.2.1.1.22.15.3
warning15-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning15 3 }

-- 1.3.6.1.4.1.11.2.3.9.4.2.1.1.22.16.1
warning16-time-stamp  OBJECT-TYPE
   SYNTAX      integer
   ACCESS      read-only
   STATUS      optional
   DESCRIPTION "Contains some sort of time stamp indicating when warning 16occurred. Example time stamps include the actual time thewarning occurred (in seconds since Jan. 1, 1970), and the totalengine page count. The device POS documents the meaning of thetime stamp. "
   USE ""
   INTERACTION " None. "
   OPERATION " Not destructive."
::= { warning16 1 }

-- 1.3.6.1.4.1.11.2.3.9.4.2.1.1.22.16.2
warning16-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning16 2 }

-- 1.3.6.1.4.1.11.2.3.9.4.2.1.1.22.16.3
warning16-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning16 3 }

-- 1.3.6.1.4.1.11.2.3.9.4.2.1.1.22.17.1
warning17-time-stamp  OBJECT-TYPE
   SYNTAX      integer
   ACCESS      read-only
   STATUS      optional
   DESCRIPTION "Contains some sort of time stamp indicating when warning 17occurred. Example time stamps include the actual time thewarning occurred (in seconds since Jan. 1, 1970), and the totalengine page count. The device POS documents the meaning of thetime stamp. "
   USE ""
   INTERACTION " None. "
   OPERATION " Not destructive."
::= { warning17 1 }

-- 1.3.6.1.4.1.11.2.3.9.4.2.1.1.22.17.2
warning17-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning17 2 }

-- 1.3.6.1.4.1.11.2.3.9.4.2.1.1.22.17.3
warning17-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning17 3 }

-- 1.3.6.1.4.1.11.2.3.9.4.2.1.1.22.18.1
warning18-time-stamp  OBJECT-TYPE
   SYNTAX      integer
   ACCESS      read-only
   STATUS      optional
   DESCRIPTION "Contains some sort of time stamp indicating when warning 18occurred. Example time stamps include the actual time thewarning occurred (in seconds since Jan. 1, 1970), and the totalengine page count. The device POS documents the meaning of thetime stamp. "
   USE ""
   INTERACTION " None. "
   OPERATION " Not destructive."
::= { warning18 1 }

-- 1.3.6.1.4.1.11.2.3.9.4.2.1.1.22.18.2
warning18-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning18 2 }

-- 1.3.6.1.4.1.11.2.3.9.4.2.1.1.22.18.3
warning18-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning18 3 }

-- 1.3.6.1.4.1.11.2.3.9.4.2.1.1.22.19.1
warning19-time-stamp  OBJECT-TYPE
   SYNTAX      integer
   ACCESS      read-only
   STATUS      optional
   DESCRIPTION "Contains some sort of time stamp indicating when warning 19occurred. Example time stamps include the actual time thewarning occurred (in seconds since Jan. 1, 1970), and the totalengine page count. The device POS documents the meaning of thetime stamp. "
   USE ""
   INTERACTION " None. "
   OPERATION " Not destructive."
::= { warning19 1 }

-- 1.3.6.1.4.1.11.2.3.9.4.2.1.1.22.19.2
warning19-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning19 2 }

-- 1.3.6.1.4.1.11.2.3.9.4.2.1.1.22.19.3
warning19-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning19 3 }

-- 1.3.6.1.4.1.11.2.3.9.4.2.1.1.22.2.1
warning2-time-stamp  OBJECT-TYPE
   SYNTAX      integer
   ACCESS      read-only
   STATUS      optional
   DESCRIPTION "Contains some sort of time stamp indicating when warning 2occurred. Example time stamps include the actual time thewarning occurred (in seconds since Jan. 1, 1970), and the totalengine page count. The device POS documents the meaning of thetime stamp. "
   USE ""
   INTERACTION " None. "
   OPERATION " Not destructive."
::= { warning2 1 }

-- 1.3.6.1.4.1.11.2.3.9.4.2.1.1.22.2.2
warning2-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning2 2 }

-- 1.3.6.1.4.1.11.2.3.9.4.2.1.1.22.2.3
warning2-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning2 3 }

-- 1.3.6.1.4.1.11.2.3.9.4.2.1.1.22.20.1
warning20-time-stamp  OBJECT-TYPE
   SYNTAX      integer
   ACCESS      read-only
   STATUS      optional
   DESCRIPTION "Contains some sort of time stamp indicating when warning 20occurred. Example time stamps include the actual time thewarning occurred (in seconds since Jan. 1, 1970), and the totalengine page count. The device POS documents the meaning of thetime stamp. "
   USE ""
   INTERACTION " None. "
   OPERATION " Not destructive."
::= { warning20 1 }

-- 1.3.6.1.4.1.11.2.3.9.4.2.1.1.22.20.2
warning20-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning20 2 }

-- 1.3.6.1.4.1.11.2.3.9.4.2.1.1.22.20.3
warning20-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning20 3 }

-- 1.3.6.1.4.1.11.2.3.9.4.2.1.1.22.21.1
warning21-time-stamp  OBJECT-TYPE
   SYNTAX      integer
   ACCESS      read-only
   STATUS      optional
   DESCRIPTION "Contains some sort of time stamp indicating when warning 21occurred. Example time stamps include the actual time thewarning occurred (in seconds since Jan. 1, 1970), and the totalengine page count. The device POS documents the meaning of thetime stamp. "
   USE ""
   INTERACTION " None. "
   OPERATION " Not destructive."
::= { warning21 1 }

-- 1.3.6.1.4.1.11.2.3.9.4.2.1.1.22.21.2
warning21-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning21 2 }

-- 1.3.6.1.4.1.11.2.3.9.4.2.1.1.22.21.3
warning21-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning21 3 }

-- 1.3.6.1.4.1.11.2.3.9.4.2.1.1.22.22.1
warning22-time-stamp  OBJECT-TYPE
   SYNTAX      integer
   ACCESS      read-only
   STATUS      optional
   DESCRIPTION "Contains some sort of time stamp indicating when warning 22occurred. Example time stamps include the actual time thewarning occurred (in seconds since Jan. 1, 1970), and the totalengine page count. The device POS documents the meaning of thetime stamp. "
   USE ""
   INTERACTION " None. "
   OPERATION " Not destructive."
::= { warning22 1 }

-- 1.3.6.1.4.1.11.2.3.9.4.2.1.1.22.22.2
warning22-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning22 2 }

-- 1.3.6.1.4.1.11.2.3.9.4.2.1.1.22.22.3
warning22-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning22 3 }

-- 1.3.6.1.4.1.11.2.3.9.4.2.1.1.22.23.1
warning23-time-stamp  OBJECT-TYPE
   SYNTAX      integer
   ACCESS      read-only
   STATUS      optional
   DESCRIPTION "Contains some sort of time stamp indicating when warning 23occurred. Example time stamps include the actual time thewarning occurred (in seconds since Jan. 1, 1970), and the totalengine page count. The device POS documents the meaning of thetime stamp. "
   USE ""
   INTERACTION " None. "
   OPERATION " Not destructive."
::= { warning23 1 }

-- 1.3.6.1.4.1.11.2.3.9.4.2.1.1.22.23.2
warning23-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning23 2 }

-- 1.3.6.1.4.1.11.2.3.9.4.2.1.1.22.23.3
warning23-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning23 3 }

-- 1.3.6.1.4.1.11.2.3.9.4.2.1.1.22.24.1
warning24-time-stamp  OBJECT-TYPE
   SYNTAX      integer
   ACCESS      read-only
   STATUS      optional
   DESCRIPTION "Contains some sort of time stamp indicating when warning 24occurred. Example time stamps include the actual time thewarning occurred (in seconds since Jan. 1, 1970), and the totalengine page count. The device POS documents the meaning of thetime stamp. "
   USE ""
   INTERACTION " None. "
   OPERATION " Not destructive."
::= { warning24 1 }

-- 1.3.6.1.4.1.11.2.3.9.4.2.1.1.22.24.2
warning24-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning24 2 }

-- 1.3.6.1.4.1.11.2.3.9.4.2.1.1.22.24.3
warning24-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning24 3 }

-- 1.3.6.1.4.1.11.2.3.9.4.2.1.1.22.25.1
warning25-time-stamp  OBJECT-TYPE
   SYNTAX      integer
   ACCESS      read-only
   STATUS      optional
   DESCRIPTION "Contains some sort of time stamp indicating when warning 25occurred. Example time stamps include the actual time thewarning occurred (in seconds since Jan. 1, 1970), and the totalengine page count. The device POS documents the meaning of thetime stamp. "
   USE ""
   INTERACTION " None. "
   OPERATION " Not destructive."
::= { warning25 1 }

-- 1.3.6.1.4.1.11.2.3.9.4.2.1.1.22.25.2
warning25-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning25 2 }

-- 1.3.6.1.4.1.11.2.3.9.4.2.1.1.22.25.3
warning25-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning25 3 }

-- 1.3.6.1.4.1.11.2.3.9.4.2.1.1.22.26.1
warning26-time-stamp  OBJECT-TYPE
   SYNTAX      integer
   ACCESS      read-only
   STATUS      optional
   DESCRIPTION "Contains some sort of time stamp indicating when warning 26occurred. Example time stamps include the actual time thewarning occurred (in seconds since Jan. 1, 1970), and the totalengine page count. The device POS documents the meaning of thetime stamp. "
   USE ""
   INTERACTION " None. "
   OPERATION " Not destructive."
::= { warning26 1 }

-- 1.3.6.1.4.1.11.2.3.9.4.2.1.1.22.26.2
warning26-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning26 2 }

-- 1.3.6.1.4.1.11.2.3.9.4.2.1.1.22.26.3
warning26-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning26 3 }

-- 1.3.6.1.4.1.11.2.3.9.4.2.1.1.22.27.1
warning27-time-stamp  OBJECT-TYPE
   SYNTAX      integer
   ACCESS      read-only
   STATUS      optional
   DESCRIPTION "Contains some sort of time stamp indicating when warning 27occurred. Example time stamps include the actual time thewarning occurred (in seconds since Jan. 1, 1970), and the totalengine page count. The device POS documents the meaning of thetime stamp. "
   USE ""
   INTERACTION " None. "
   OPERATION " Not destructive."
::= { warning27 1 }

-- 1.3.6.1.4.1.11.2.3.9.4.2.1.1.22.27.2
warning27-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning27 2 }

-- 1.3.6.1.4.1.11.2.3.9.4.2.1.1.22.27.3
warning27-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning27 3 }

-- 1.3.6.1.4.1.11.2.3.9.4.2.1.1.22.28.1
warning28-time-stamp  OBJECT-TYPE
   SYNTAX      integer
   ACCESS      read-only
   STATUS      optional
   DESCRIPTION "Contains some sort of time stamp indicating when warning 28occurred. Example time stamps include the actual time thewarning occurred (in seconds since Jan. 1, 1970), and the totalengine page count. The device POS documents the meaning of thetime stamp. "
   USE ""
   INTERACTION " None. "
   OPERATION " Not destructive."
::= { warning28 1 }

-- 1.3.6.1.4.1.11.2.3.9.4.2.1.1.22.28.2
warning28-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning28 2 }

-- 1.3.6.1.4.1.11.2.3.9.4.2.1.1.22.28.3
warning28-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning28 3 }

-- 1.3.6.1.4.1.11.2.3.9.4.2.1.1.22.29.1
warning29-time-stamp  OBJECT-TYPE
   SYNTAX      integer
   ACCESS      read-only
   STATUS      optional
   DESCRIPTION "Contains some sort of time stamp indicating when warning 29occurred. Example time stamps include the actual time thewarning occurred (in seconds since Jan. 1, 1970), and the totalengine page count. The device POS documents the meaning of thetime stamp. "
   USE ""
   INTERACTION " None. "
   OPERATION " Not destructive."
::= { warning29 1 }

-- 1.3.6.1.4.1.11.2.3.9.4.2.1.1.22.29.2
warning29-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning29 2 }

-- 1.3.6.1.4.1.11.2.3.9.4.2.1.1.22.29.3
warning29-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning29 3 }

-- 1.3.6.1.4.1.11.2.3.9.4.2.1.1.22.3.1
warning3-time-stamp  OBJECT-TYPE
   SYNTAX      integer
   ACCESS      read-only
   STATUS      optional
   DESCRIPTION "Contains some sort of time stamp indicating when warning 3occurred. Example time stamps include the actual time thewarning occurred (in seconds since Jan. 1, 1970), and the totalengine page count. The device POS documents the meaning of thetime stamp. "
   USE ""
   INTERACTION " None. "
   OPERATION " Not destructive."
::= { warning3 1 }

-- 1.3.6.1.4.1.11.2.3.9.4.2.1.1.22.3.2
warning3-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning3 2 }

-- 1.3.6.1.4.1.11.2.3.9.4.2.1.1.22.3.3
warning3-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning3 3 }

-- 1.3.6.1.4.1.11.2.3.9.4.2.1.1.22.30.1
warning30-time-stamp  OBJECT-TYPE
   SYNTAX      integer
   ACCESS      read-only
   STATUS      optional
   DESCRIPTION "Contains some sort of time stamp indicating when warning 30occurred. Example time stamps include the actual time thewarning occurred (in seconds since Jan. 1, 1970), and the totalengine page count. The device POS documents the meaning of thetime stamp. "
   USE ""
   INTERACTION " None. "
   OPERATION " Not destructive."
::= { warning30 1 }

-- 1.3.6.1.4.1.11.2.3.9.4.2.1.1.22.30.2
warning30-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning30 2 }

-- 1.3.6.1.4.1.11.2.3.9.4.2.1.1.22.30.3
warning30-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning30 3 }

-- 1.3.6.1.4.1.11.2.3.9.4.2.1.1.22.31.1
warning31-time-stamp  OBJECT-TYPE
   SYNTAX      integer
   ACCESS      read-only
   STATUS      optional
   DESCRIPTION "Contains some sort of time stamp indicating when warning 31occurred. Example time stamps include the actual time thewarning occurred (in seconds since Jan. 1, 1970), and the totalengine page count. The device POS documents the meaning of thetime stamp. "
   USE ""
   INTERACTION " None. "
   OPERATION " Not destructive."
::= { warning31 1 }

-- 1.3.6.1.4.1.11.2.3.9.4.2.1.1.22.31.2
warning31-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning31 2 }

-- 1.3.6.1.4.1.11.2.3.9.4.2.1.1.22.31.3
warning31-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning31 3 }

-- 1.3.6.1.4.1.11.2.3.9.4.2.1.1.22.32.1
warning32-time-stamp  OBJECT-TYPE
   SYNTAX      integer
   ACCESS      read-only
   STATUS      optional
   DESCRIPTION "Contains some sort of time stamp indicating when warning 32occurred. Example time stamps include the actual time thewarning occurred (in seconds since Jan. 1, 1970), and the totalengine page count. The device POS documents the meaning of thetime stamp. "
   USE ""
   INTERACTION " None. "
   OPERATION " Not destructive."
::= { warning32 1 }

-- 1.3.6.1.4.1.11.2.3.9.4.2.1.1.22.32.2
warning32-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning32 2 }

-- 1.3.6.1.4.1.11.2.3.9.4.2.1.1.22.32.3
warning32-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning32 3 }

-- 1.3.6.1.4.1.11.2.3.9.4.2.1.1.22.33.1
warning33-time-stamp  OBJECT-TYPE
   SYNTAX      integer
   ACCESS      read-only
   STATUS      optional
   DESCRIPTION "Contains some sort of time stamp indicating when warning 33occurred. Example time stamps include the actual time thewarning occurred (in seconds since Jan. 1, 1970), and the totalengine page count. The device POS documents the meaning of thetime stamp. "
   USE ""
   INTERACTION " None. "
   OPERATION " Not destructive."
::= { warning33 1 }

-- 1.3.6.1.4.1.11.2.3.9.4.2.1.1.22.33.2
warning33-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning33 2 }

-- 1.3.6.1.4.1.11.2.3.9.4.2.1.1.22.33.3
warning33-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning33 3 }

-- 1.3.6.1.4.1.11.2.3.9.4.2.1.1.22.34.1
warning34-time-stamp  OBJECT-TYPE
   SYNTAX      integer
   ACCESS      read-only
   STATUS      optional
   DESCRIPTION "Contains some sort of time stamp indicating when warning 34occurred. Example time stamps include the actual time thewarning occurred (in seconds since Jan. 1, 1970), and the totalengine page count. The device POS documents the meaning of thetime stamp. "
   USE ""
   INTERACTION " None. "
   OPERATION " Not destructive."
::= { warning34 1 }

-- 1.3.6.1.4.1.11.2.3.9.4.2.1.1.22.34.2
warning34-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning34 2 }

-- 1.3.6.1.4.1.11.2.3.9.4.2.1.1.22.34.3
warning34-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning34 3 }

-- 1.3.6.1.4.1.11.2.3.9.4.2.1.1.22.35.1
warning35-time-stamp  OBJECT-TYPE
   SYNTAX      integer
   ACCESS      read-only
   STATUS      optional
   DESCRIPTION "Contains some sort of time stamp indicating when warning 35occurred. Example time stamps include the actual time thewarning occurred (in seconds since Jan. 1, 1970), and the totalengine page count. The device POS documents the meaning of thetime stamp. "
   USE ""
   INTERACTION " None. "
   OPERATION " Not destructive."
::= { warning35 1 }

-- 1.3.6.1.4.1.11.2.3.9.4.2.1.1.22.35.2
warning35-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning35 2 }

-- 1.3.6.1.4.1.11.2.3.9.4.2.1.1.22.35.3
warning35-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning35 3 }

-- 1.3.6.1.4.1.11.2.3.9.4.2.1.1.22.36.1
warning36-time-stamp  OBJECT-TYPE
   SYNTAX      integer
   ACCESS      read-only
   STATUS      optional
   DESCRIPTION "Contains some sort of time stamp indicating when warning 36occurred. Example time stamps include the actual time thewarning occurred (in seconds since Jan. 1, 1970), and the totalengine page count. The device POS documents the meaning of thetime stamp. "
   USE ""
   INTERACTION " None. "
   OPERATION " Not destructive."
::= { warning36 1 }

-- 1.3.6.1.4.1.11.2.3.9.4.2.1.1.22.36.2
warning36-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning36 2 }

-- 1.3.6.1.4.1.11.2.3.9.4.2.1.1.22.36.3
warning36-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning36 3 }

-- 1.3.6.1.4.1.11.2.3.9.4.2.1.1.22.37.1
warning37-time-stamp  OBJECT-TYPE
   SYNTAX      integer
   ACCESS      read-only
   STATUS      optional
   DESCRIPTION "Contains some sort of time stamp indicating when warning 37occurred. Example time stamps include the actual time thewarning occurred (in seconds since Jan. 1, 1970), and the totalengine page count. The device POS documents the meaning of thetime stamp. "
   USE ""
   INTERACTION " None. "
   OPERATION " Not destructive."
::= { warning37 1 }

-- 1.3.6.1.4.1.11.2.3.9.4.2.1.1.22.37.2
warning37-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning37 2 }

-- 1.3.6.1.4.1.11.2.3.9.4.2.1.1.22.37.3
warning37-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning37 3 }

-- 1.3.6.1.4.1.11.2.3.9.4.2.1.1.22.38.1
warning38-time-stamp  OBJECT-TYPE
   SYNTAX      integer
   ACCESS      read-only
   STATUS      optional
   DESCRIPTION "Contains some sort of time stamp indicating when warning 38occurred. Example time stamps include the actual time thewarning occurred (in seconds since Jan. 1, 1970), and the totalengine page count. The device POS documents the meaning of thetime stamp. "
   USE ""
   INTERACTION " None. "
   OPERATION " Not destructive."
::= { warning38 1 }

-- 1.3.6.1.4.1.11.2.3.9.4.2.1.1.22.38.2
warning38-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning38 2 }

-- 1.3.6.1.4.1.11.2.3.9.4.2.1.1.22.38.3
warning38-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning38 3 }

-- 1.3.6.1.4.1.11.2.3.9.4.2.1.1.22.39.1
warning39-time-stamp  OBJECT-TYPE
   SYNTAX      integer
   ACCESS      read-only
   STATUS      optional
   DESCRIPTION "Contains some sort of time stamp indicating when warning 39occurred. Example time stamps include the actual time thewarning occurred (in seconds since Jan. 1, 1970), and the totalengine page count. The device POS documents the meaning of thetime stamp. "
   USE ""
   INTERACTION " None. "
   OPERATION " Not destructive."
::= { warning39 1 }

-- 1.3.6.1.4.1.11.2.3.9.4.2.1.1.22.39.2
warning39-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning39 2 }

-- 1.3.6.1.4.1.11.2.3.9.4.2.1.1.22.39.3
warning39-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning39 3 }

-- 1.3.6.1.4.1.11.2.3.9.4.2.1.1.22.4.1
warning4-time-stamp  OBJECT-TYPE
   SYNTAX      integer
   ACCESS      read-only
   STATUS      optional
   DESCRIPTION "Contains some sort of time stamp indicating when warning 4occurred. Example time stamps include the actual time thewarning occurred (in seconds since Jan. 1, 1970), and the totalengine page count. The device POS documents the meaning of thetime stamp. "
   USE ""
   INTERACTION " None. "
   OPERATION " Not destructive."
::= { warning4 1 }

-- 1.3.6.1.4.1.11.2.3.9.4.2.1.1.22.4.2
warning4-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning4 2 }

-- 1.3.6.1.4.1.11.2.3.9.4.2.1.1.22.4.3
warning4-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning4 3 }

-- 1.3.6.1.4.1.11.2.3.9.4.2.1.1.22.40.1
warning40-time-stamp  OBJECT-TYPE
   SYNTAX      integer
   ACCESS      read-only
   STATUS      optional
   DESCRIPTION "Contains some sort of time stamp indicating when warning 40occurred. Example time stamps include the actual time thewarning occurred (in seconds since Jan. 1, 1970), and the totalengine page count. The device POS documents the meaning of thetime stamp. "
   USE ""
   INTERACTION " None. "
   OPERATION " Not destructive."
::= { warning40 1 }

-- 1.3.6.1.4.1.11.2.3.9.4.2.1.1.22.40.2
warning40-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning40 2 }

-- 1.3.6.1.4.1.11.2.3.9.4.2.1.1.22.40.3
warning40-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning40 3 }

-- 1.3.6.1.4.1.11.2.3.9.4.2.1.1.22.41.1
warning41-time-stamp  OBJECT-TYPE
   SYNTAX      integer
   ACCESS      read-only
   STATUS      optional
   DESCRIPTION "Contains some sort of time stamp indicating when warning 41occurred. Example time stamps include the actual time thewarning occurred (in seconds since Jan. 1, 1970), and the totalengine page count. The device POS documents the meaning of thetime stamp. "
   USE ""
   INTERACTION " None. "
   OPERATION " Not destructive."
::= { warning41 1 }

-- 1.3.6.1.4.1.11.2.3.9.4.2.1.1.22.41.2
warning41-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning41 2 }

-- 1.3.6.1.4.1.11.2.3.9.4.2.1.1.22.41.3
warning41-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning41 3 }

-- 1.3.6.1.4.1.11.2.3.9.4.2.1.1.22.42.1
warning42-time-stamp  OBJECT-TYPE
   SYNTAX      integer
   ACCESS      read-only
   STATUS      optional
   DESCRIPTION "Contains some sort of time stamp indicating when warning 42occurred. Example time stamps include the actual time thewarning occurred (in seconds since Jan. 1, 1970), and the totalengine page count. The device POS documents the meaning of thetime stamp. "
   USE ""
   INTERACTION " None. "
   OPERATION " Not destructive."
::= { warning42 1 }

-- 1.3.6.1.4.1.11.2.3.9.4.2.1.1.22.42.2
warning42-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning42 2 }

-- 1.3.6.1.4.1.11.2.3.9.4.2.1.1.22.42.3
warning42-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning42 3 }

-- 1.3.6.1.4.1.11.2.3.9.4.2.1.1.22.43.1
warning43-time-stamp  OBJECT-TYPE
   SYNTAX      integer
   ACCESS      read-only
   STATUS      optional
   DESCRIPTION "Contains some sort of time stamp indicating when warning 43occurred. Example time stamps include the actual time thewarning occurred (in seconds since Jan. 1, 1970), and the totalengine page count. The device POS documents the meaning of thetime stamp. "
   USE ""
   INTERACTION " None. "
   OPERATION " Not destructive."
::= { warning43 1 }

-- 1.3.6.1.4.1.11.2.3.9.4.2.1.1.22.43.2
warning43-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning43 2 }

-- 1.3.6.1.4.1.11.2.3.9.4.2.1.1.22.43.3
warning43-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning43 3 }

-- 1.3.6.1.4.1.11.2.3.9.4.2.1.1.22.44.1
warning44-time-stamp  OBJECT-TYPE
   SYNTAX      integer
   ACCESS      read-only
   STATUS      optional
   DESCRIPTION "Contains some sort of time stamp indicating when warning 44occurred. Example time stamps include the actual time thewarning occurred (in seconds since Jan. 1, 1970), and the totalengine page count. The device POS documents the meaning of thetime stamp. "
   USE ""
   INTERACTION " None. "
   OPERATION " Not destructive."
::= { warning44 1 }

-- 1.3.6.1.4.1.11.2.3.9.4.2.1.1.22.44.2
warning44-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning44 2 }

-- 1.3.6.1.4.1.11.2.3.9.4.2.1.1.22.44.3
warning44-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning44 3 }

-- 1.3.6.1.4.1.11.2.3.9.4.2.1.1.22.45.1
warning45-time-stamp  OBJECT-TYPE
   SYNTAX      integer
   ACCESS      read-only
   STATUS      optional
   DESCRIPTION "Contains some sort of time stamp indicating when warning 45occurred. Example time stamps include the actual time thewarning occurred (in seconds since Jan. 1, 1970), and the totalengine page count. The device POS documents the meaning of thetime stamp. "
   USE ""
   INTERACTION " None. "
   OPERATION " Not destructive."
::= { warning45 1 }

-- 1.3.6.1.4.1.11.2.3.9.4.2.1.1.22.45.2
warning45-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning45 2 }

-- 1.3.6.1.4.1.11.2.3.9.4.2.1.1.22.45.3
warning45-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning45 3 }

-- 1.3.6.1.4.1.11.2.3.9.4.2.1.1.22.46.1
warning46-time-stamp  OBJECT-TYPE
   SYNTAX      integer
   ACCESS      read-only
   STATUS      optional
   DESCRIPTION "Contains some sort of time stamp indicating when warning 46occurred. Example time stamps include the actual time thewarning occurred (in seconds since Jan. 1, 1970), and the totalengine page count. The device POS documents the meaning of thetime stamp. "
   USE ""
   INTERACTION " None. "
   OPERATION " Not destructive."
::= { warning46 1 }

-- 1.3.6.1.4.1.11.2.3.9.4.2.1.1.22.46.2
warning46-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning46 2 }

-- 1.3.6.1.4.1.11.2.3.9.4.2.1.1.22.46.3
warning46-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning46 3 }

-- 1.3.6.1.4.1.11.2.3.9.4.2.1.1.22.47.1
warning47-time-stamp  OBJECT-TYPE
   SYNTAX      integer
   ACCESS      read-only
   STATUS      optional
   DESCRIPTION "Contains some sort of time stamp indicating when warning 47occurred. Example time stamps include the actual time thewarning occurred (in seconds since Jan. 1, 1970), and the totalengine page count. The device POS documents the meaning of thetime stamp. "
   USE ""
   INTERACTION " None. "
   OPERATION " Not destructive."
::= { warning47 1 }

-- 1.3.6.1.4.1.11.2.3.9.4.2.1.1.22.47.2
warning47-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning47 2 }

-- 1.3.6.1.4.1.11.2.3.9.4.2.1.1.22.47.3
warning47-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning47 3 }

-- 1.3.6.1.4.1.11.2.3.9.4.2.1.1.22.48.1
warning48-time-stamp  OBJECT-TYPE
   SYNTAX      integer
   ACCESS      read-only
   STATUS      optional
   DESCRIPTION "Contains some sort of time stamp indicating when warning 48occurred. Example time stamps include the actual time thewarning occurred (in seconds since Jan. 1, 1970), and the totalengine page count. The device POS documents the meaning of thetime stamp. "
   USE ""
   INTERACTION " None. "
   OPERATION " Not destructive."
::= { warning48 1 }

-- 1.3.6.1.4.1.11.2.3.9.4.2.1.1.22.48.2
warning48-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning48 2 }

-- 1.3.6.1.4.1.11.2.3.9.4.2.1.1.22.48.3
warning48-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning48 3 }

-- 1.3.6.1.4.1.11.2.3.9.4.2.1.1.22.49.1
warning49-time-stamp  OBJECT-TYPE
   SYNTAX      integer
   ACCESS      read-only
   STATUS      optional
   DESCRIPTION "Contains some sort of time stamp indicating when warning 49occurred. Example time stamps include the actual time thewarning occurred (in seconds since Jan. 1, 1970), and the totalengine page count. The device POS documents the meaning of thetime stamp. "
   USE ""
   INTERACTION " None. "
   OPERATION " Not destructive."
::= { warning49 1 }

-- 1.3.6.1.4.1.11.2.3.9.4.2.1.1.22.49.2
warning49-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning49 2 }

-- 1.3.6.1.4.1.11.2.3.9.4.2.1.1.22.49.3
warning49-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning49 3 }

-- 1.3.6.1.4.1.11.2.3.9.4.2.1.1.22.5.1
warning5-time-stamp  OBJECT-TYPE
   SYNTAX      integer
   ACCESS      read-only
   STATUS      optional
   DESCRIPTION "Contains some sort of time stamp indicating when warning 5occurred. Example time stamps include the actual time thewarning occurred (in seconds since Jan. 1, 1970), and the totalengine page count. The device POS documents the meaning of thetime stamp. "
   USE ""
   INTERACTION " None. "
   OPERATION " Not destructive."
::= { warning5 1 }

-- 1.3.6.1.4.1.11.2.3.9.4.2.1.1.22.5.2
warning5-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning5 2 }

-- 1.3.6.1.4.1.11.2.3.9.4.2.1.1.22.5.3
warning5-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning5 3 }

-- 1.3.6.1.4.1.11.2.3.9.4.2.1.1.22.50.1
warning50-time-stamp  OBJECT-TYPE
   SYNTAX      integer
   ACCESS      read-only
   STATUS      optional
   DESCRIPTION "Contains some sort of time stamp indicating when warning 50occurred. Example time stamps include the actual time thewarning occurred (in seconds since Jan. 1, 1970), and the totalengine page count. The device POS documents the meaning of thetime stamp. "
   USE ""
   INTERACTION " None. "
   OPERATION " Not destructive."
::= { warning50 1 }

-- 1.3.6.1.4.1.11.2.3.9.4.2.1.1.22.50.2
warning50-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning50 2 }

-- 1.3.6.1.4.1.11.2.3.9.4.2.1.1.22.50.3
warning50-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning50 3 }

-- 1.3.6.1.4.1.11.2.3.9.4.2.1.1.22.6.1
warning6-time-stamp  OBJECT-TYPE
   SYNTAX      integer
   ACCESS      read-only
   STATUS      optional
   DESCRIPTION "Contains some sort of time stamp indicating when warning 6occurred. Example time stamps include the actual time thewarning occurred (in seconds since Jan. 1, 1970), and the totalengine page count. The device POS documents the meaning of thetime stamp. "
   USE ""
   INTERACTION " None. "
   OPERATION " Not destructive."
::= { warning6 1 }

-- 1.3.6.1.4.1.11.2.3.9.4.2.1.1.22.6.2
warning6-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning6 2 }

-- 1.3.6.1.4.1.11.2.3.9.4.2.1.1.22.6.3
warning6-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning6 3 }

-- 1.3.6.1.4.1.11.2.3.9.4.2.1.1.22.7.1
warning7-time-stamp  OBJECT-TYPE
   SYNTAX      integer
   ACCESS      read-only
   STATUS      optional
   DESCRIPTION "Contains some sort of time stamp indicating when warning 7occurred. Example time stamps include the actual time thewarning occurred (in seconds since Jan. 1, 1970), and the totalengine page count. The device POS documents the meaning of thetime stamp. "
   USE ""
   INTERACTION " None. "
   OPERATION " Not destructive."
::= { warning7 1 }

-- 1.3.6.1.4.1.11.2.3.9.4.2.1.1.22.7.2
warning7-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning7 2 }

-- 1.3.6.1.4.1.11.2.3.9.4.2.1.1.22.7.3
warning7-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning7 3 }

-- 1.3.6.1.4.1.11.2.3.9.4.2.1.1.22.8.1
warning8-time-stamp  OBJECT-TYPE
   SYNTAX      integer
   ACCESS      read-only
   STATUS      optional
   DESCRIPTION "Contains some sort of time stamp indicating when warning 8occurred. Example time stamps include the actual time thewarning occurred (in seconds since Jan. 1, 1970), and the totalengine page count. The device POS documents the meaning of thetime stamp. "
   USE ""
   INTERACTION " None. "
   OPERATION " Not destructive."
::= { warning8 1 }

-- 1.3.6.1.4.1.11.2.3.9.4.2.1.1.22.8.2
warning8-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning8 2 }

-- 1.3.6.1.4.1.11.2.3.9.4.2.1.1.22.8.3
warning8-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning8 3 }

-- 1.3.6.1.4.1.11.2.3.9.4.2.1.1.22.9.1
warning9-time-stamp  OBJECT-TYPE
   SYNTAX      integer
   ACCESS      read-only
   STATUS      optional
   DESCRIPTION "Contains some sort of time stamp indicating when warning 9occurred. Example time stamps include the actual time thewarning occurred (in seconds since Jan. 1, 1970), and the totalengine page count. The device POS documents the meaning of thetime stamp. "
   USE ""
   INTERACTION " None. "
   OPERATION " Not destructive."
::= { warning9 1 }

-- 1.3.6.1.4.1.11.2.3.9.4.2.1.1.22.9.2
warning9-code  OBJECT-TYPE
   SYNTAX      integer
   ACCESS      read-only
   STATUS      optional
   DESCRIPTION "Contains a device specific warning code. Each device POS shouldlist what warnings are logged to the warning log and themeaning of each supported warning code value. "
   USE ""
   INTERACTION " None. "
   OPERATION " Not destructive."
::= { warning9 2 }

-- 1.3.6.1.4.1.11.2.3.9.4.2.1.1.22.9.3
warning9-date-time  OBJECT-TYPE
   SYNTAX      binary
   ACCESS      read-only
   STATUS      optional
   DESCRIPTION "This item contains the date and the time at which an warningoccurred. The values returned will be in hexadecimal. If thedate is 2004-Jul-13 and the time is 03:15 a.m., we get 04 07 0d03 0f where, \\04 (hex) - corresponds to the year 2004. \\07 (hex) - corresponds to month, 07 \\0d (hex) - corresponds to date, 13 \\03 (hex) - corresponds to hour, 3 a.m. \\0f (hex) - corresponds to min, 15. \\ "
   USE ""
   INTERACTION "  "
   OPERATION " Not destructive."
::= { warning9 3 }

-- 1.3.6.1.4.1.11.2.3.9.4.2.1.1.23.1.1
supports-pjl-user-groups  OBJECT-TYPE
   SYNTAX      enumerated { eFalse (1) , eTrue (2) }
   ACCESS      read-only
   STATUS      optional
   DESCRIPTION "Returns eTrue if the device is able to process PJL user groupvariables. See the PJL Technical Reference for the propersyntax for setting these variables. Because there may be manyuser groups in some environments, this object allows a clientapplication to optimize the print job by including user groupsonly when the device is able to process them. "
   USE ""
   INTERACTION " None. "
   OPERATION " Accessing this object identifier is NOT destructive in anymanner."
::= { settings-security 1 }

-- 1.3.6.1.4.1.11.2.3.9.4.2.1.1.25.1
toner-miser-plus-value  OBJECT-TYPE
   SYNTAX      string
   ACCESS      write-only
   STATUS      optional
   DESCRIPTION "This object is used to enable/disable toner miser plusfeature. "
   USE ""
   INTERACTION " Setting this object will cause a status of &lt;OK&gt; to bereturned. "
   OPERATION " Not destructive."
::= { settings-system2 1 }

-- 1.3.6.1.4.1.11.2.3.9.4.2.1.1.25.17
protect-ews-info-tab  OBJECT-TYPE
   SYNTAX      enumerated { eOff (1) , eOn (2) }
   ACCESS      read-write
   STATUS      optional
   DESCRIPTION "This PML object is used by the WJA tool to allow administratorsto enable or disable EWS information tab protection. When thisoption in selected/turned on the user will not be able toaccess anything on the EWS without logging in with the EWSdevice <<hidden>>(in case the EWS device <<hidden>> is configured).If the option is turned off the user will be able to access theinformation tab on the EWS page without providing the EWSdevice <<hidden>>(in case the EWS device <<hidden>> is configured),for all other tabs on the EWS page the user will have to loginwith EWS device <<hidden>>. "
   USE ""
   INTERACTION " None. "
   OPERATION " Writing this value to eOff will disable EWS information tabprotection. Writing this value to eOn will enable EWSinformation tab protection. Reading this object identifier isNOT destructive in any manner."
::= { settings-system2 17 }

-- 1.3.6.1.4.1.11.2.3.9.4.2.1.1.25.19
eprint-opt-in  OBJECT-TYPE
   SYNTAX      enumerated { eOff (1) , eOn (2) }
   ACCESS      read-write
   STATUS      optional
   DESCRIPTION "This object is the master switch for the ePrint feature. Bydefault this should be eOff(1). This differs fromEPRINT-ENABLED in that ePrint connot be registered with thecloud when this is diabled while EPRINT-ENABLED allowsregistration and temporary disablement. "
   USE ""
   INTERACTION " None. "
   OPERATION " Not Destructive."
::= { settings-system2 19 }

-- 1.3.6.1.4.1.11.2.3.9.4.2.1.1.25.2
toner-miser-plus-supported  OBJECT-TYPE
   SYNTAX      enumerated { eOff (1) , eOn (2) }
   ACCESS      read-only
   STATUS      optional
   DESCRIPTION "The supported values are ON and OFF. The toner miser plusfeature is turned OFF by default. "
   USE ""
   INTERACTION " Get on this object will cause a status of &lt;OK&gt; to be returned. "
   OPERATION " Not destructive."
::= { settings-system2 2 }

-- 1.3.6.1.4.1.11.2.3.9.4.2.1.1.25.20
eprint-enabled  OBJECT-TYPE
   SYNTAX      enumerated { eOff (1) , eOn (2) }
   ACCESS      read-write
   STATUS      optional
   DESCRIPTION "Returns the current setting of the ePrint feature. "
   USE ""
   INTERACTION " None. "
   OPERATION " Not Destructive."
::= { settings-system2 20 }

-- 1.3.6.1.4.1.11.2.3.9.4.2.1.1.25.21
eprint-email-address  OBJECT-TYPE
   SYNTAX      string
   ACCESS      read-write
   STATUS      optional
   DESCRIPTION "This is the configured ePrint email address. "
   USE ""
   INTERACTION " None "
   OPERATION " Not Destructive."
::= { settings-system2 21 }

-- 1.3.6.1.4.1.11.2.3.9.4.2.1.1.25.22
eprint-email  OBJECT-TYPE
   SYNTAX      enumerated { eOff (1) , eOn (2) }
   ACCESS      read-write
   STATUS      optional
   DESCRIPTION "This object reports the current setting of ePrint e-mail. "
   USE ""
   INTERACTION " None. "
   OPERATION " Not Destructive."
::= { settings-system2 22 }

-- 1.3.6.1.4.1.11.2.3.9.4.2.1.1.25.23
eprint-printer-code  OBJECT-TYPE
   SYNTAX      string
   ACCESS      read-write
   STATUS      optional
   DESCRIPTION "This is the configured ePrint printer code. "
   USE ""
   INTERACTION " none. "
   OPERATION " Not destructive."
::= { settings-system2 23 }

-- 1.3.6.1.4.1.11.2.3.9.4.2.1.1.25.24
eprint-hp-web-services  OBJECT-TYPE
   SYNTAX      enumerated { eOff (1) , eOn (2) }
   ACCESS      read-write
   STATUS      optional
   DESCRIPTION "This object reports the current setting of the ePrint webservices. "
   USE ""
   INTERACTION " None. "
   OPERATION " Not destructive."
::= { settings-system2 24 }

-- 1.3.6.1.4.1.11.2.3.9.4.2.1.1.25.25
eprint-jdi-interface  OBJECT-TYPE
   SYNTAX      enumerated { eJDIInterface1 (1) , eJDIInterface2 (2) , eJDIInterface3 (3) , eJDIInterface4 (4) , eJDIInterface5 (5) , eJDIInterface6 (6) , eJDIInterface7 (7) , eJDIInterface8 (8) , eJDIInterface9 (9) , eJDIInterface10 (10) }
   ACCESS      read-write
   STATUS      optional
   DESCRIPTION "This number represents the instance of jdi that has ePrintregistered. "
   USE ""
   INTERACTION " None. "
   OPERATION " Not destructive."
::= { settings-system2 25 }

-- 1.3.6.1.4.1.11.2.3.9.4.2.1.1.25.31
eprint-supported  OBJECT-TYPE
   SYNTAX      enumerated { eOff (1) , eOn (2) }
   ACCESS      read-write
   STATUS      optional
   DESCRIPTION "This object is used to indicate whether the device supportsePrint or not. By default this should be eOff(1), but will beset to eOn(2) if the device supports ePrint. "
   USE ""
   INTERACTION " none "
   OPERATION " Not Destructive."
::= { settings-system2 31 }

-- 1.3.6.1.4.1.11.2.3.9.4.2.1.1.25.32
eprint-supported-jdi  OBJECT-TYPE
   SYNTAX      enumerated { eOff (1) , eOn (2) }
   ACCESS      read-write
   STATUS      optional
   DESCRIPTION "This object is used to indicate whether the JDI supports ePrintor not. By default this should be eOff(1), but will be set toeOn(2) if JDI supports ePrint. "
   USE ""
   INTERACTION " none "
   OPERATION " Not Destructive."
::= { settings-system2 32 }

-- 1.3.6.1.4.1.11.2.3.9.4.2.1.1.3.1
model-number  OBJECT-TYPE
   SYNTAX      string
   ACCESS      read-only
   STATUS      optional
   DESCRIPTION "Identifies the device model number as listed in the HPcorporate price list (e.g. C2121A for DeskJet 500C). The stringis as specific as possible. Products should note in POS if themodel number on the CPL changes but the device reports theprevious model number. If the model number changes based on theinstalled options, the POS should indicate if only the basemodel number is returned, or if the device senses the installedoptions and returns the correct model number. If possible,encode the model number in a symbol set (like Roman-8) thatmatches the ASCII character set and limit the characters usedto ASCII characters. "
   USE ""
   INTERACTION " None. "
   OPERATION " Not destructive."
::= { id 1 }

-- 1.3.6.1.4.1.11.2.3.9.4.2.1.1.3.10
device-name  OBJECT-TYPE
   SYNTAX      string
   ACCESS      read-write , trappable
   STATUS      optional
   DESCRIPTION "User defined device name. The POS should indicate the maximumsupported string length. If the user entered string is toolong, the device will store as much as possible and will returnthe &lt;OKNearestLegal ValueSubstituted&gt;. "
   USE ""
   INTERACTION ""
   OPERATION " Not destructive."
::= { id 10 }

-- 1.3.6.1.4.1.11.2.3.9.4.2.1.1.3.11
device-location  OBJECT-TYPE
   SYNTAX      string
   ACCESS      read-write
   STATUS      optional
   DESCRIPTION "User defined device location. The POS should indicate themaximum supported string length. If the user entered string istoo long, the device will store as much as possible and willreturn the &lt;OKNearestLegal ValueSubstituted&gt;. "
   USE ""
   INTERACTION " None. "
   OPERATION " Not destructive."
::= { id 11 }

-- 1.3.6.1.4.1.11.2.3.9.4.2.1.1.3.12
asset-number  OBJECT-TYPE
   SYNTAX      string
   ACCESS      read-write
   STATUS      optional
   DESCRIPTION "User defined asset number. The POS should indicate the maximumsupported string length. If the user entered string is toolong, the device will store as much as possible and will returnthe &lt;OKNearestLegal ValueSubstituted&gt;. "
   USE ""
   INTERACTION " None. "
   OPERATION " Not destructive."
::= { id 12 }

-- 1.3.6.1.4.1.11.2.3.9.4.2.1.1.3.2
model-name  OBJECT-TYPE
   SYNTAX      string
   ACCESS      read-only
   STATUS      optional
   DESCRIPTION "Identifies the device model name (e.g. ''DeskJet 1200C''). Thestring is as specific as possible. Capitalization and spacingshould match family naming conventions. Products should note inPOS if the model name on the HP corporate price list changesbut the device reports the previous device name. If the modelname changes based on the installed options, the POS shouldindicate if only the base model name is returned, or if thedevice senses the installed options and returns the correctmodel name. If possible, encode the model name in a symbol set(like Roman-8) that matches the ASCII character set and limitthe characters used to ASCII characters. "
   USE ""
   INTERACTION " None. "
   OPERATION " Not destructive."
::= { id 2 }

-- 1.3.6.1.4.1.11.2.3.9.4.2.1.1.3.20
formatter-serial-number  OBJECT-TYPE
   SYNTAX      string
   ACCESS      read-only
   STATUS      optional
   DESCRIPTION "This object returns the formatter serial number for the device.The value returned from this object is the FORMATTERNUMBERsystem variable. If possible, encode the serial number in asymbol set (like Roman-8) that matches the ASCII character setand limit the characters used to ASCII characters. "
   USE ""
   INTERACTION " None. "
   OPERATION " Not destructive."
::= { id 20 }

-- 1.3.6.1.4.1.11.2.3.9.4.2.1.1.3.3
serial-number  OBJECT-TYPE
   SYNTAX      string
   ACCESS      read-write
   STATUS      optional
   DESCRIPTION "Identifies the serial number for the device. If theSERIAL-NUMBER object is set by the user, then setting theobject does not need to be protected. If the SERIAL-NUMBERobject is set at the factory, then the <<hidden>> objectmust be set correctly before the SERIAL-NUMBER object iswritable. If this is a writable object, the POS should indicatethe maximum supported string length. If possible, encode theserial number in a symbol set (like Roman-8) that matches theASCII character set and limit the characters used to ASCIIcharacters. "
   USE ""
   INTERACTION " Not effected by user NVRAM resets. "
   OPERATION " Not destructive."
::= { id 3 }

-- 1.3.6.1.4.1.11.2.3.9.4.2.1.1.3.5
fw-rom-datecode  OBJECT-TYPE
   SYNTAX      string
   ACCESS      read-only
   STATUS      optional
   DESCRIPTION "Identifies the base device-system firmware date code. The date codewill be encoded in the yyyymmdd format. There may be severalversions of the base device-system firmware. The date code associatedwith the version of the base device-system firmware that is being usedis reported. There may be other date code objects for otherspecific modules such as fonts, localization modules, etc.;these other datecode objects are device specific. "
   USE ""
   INTERACTION " None. "
   OPERATION " Not destructive."
::= { id 5 }

-- 1.3.6.1.4.1.11.2.3.9.4.2.1.1.3.6
fw-rom-revision  OBJECT-TYPE
   SYNTAX      string
   ACCESS      read-only
   STATUS      optional
   DESCRIPTION "This identifies the device-system code firmware ROM revision code. Theformat for a revision is major_revision.minor_revision. Theremay be other ROM revision code objects for other specific ROMssuch as font ROMs, localization ROMs, etc; these other ROMrevision code objects are device specific. "
   USE ""
   INTERACTION " None. "
   OPERATION " Not destructive."
::= { id 6 }

-- 1.3.6.1.4.1.11.2.3.9.4.2.1.1.4.3.1.2
mio1-model-name  OBJECT-TYPE
   SYNTAX      string
   ACCESS      read-only
   STATUS      optional
   DESCRIPTION "Returns product information identifying the I/O card. Example:XXXX. "
   USE ""
   INTERACTION " None. "
   OPERATION " Not destructive."
::= { mio1 2 }

-- 1.3.6.1.4.1.11.2.3.9.4.2.1.1.4.3.1.3
mio1-manufacturing-info  OBJECT-TYPE
   SYNTAX      string
   ACCESS      read-only
   STATUS      optional
   DESCRIPTION "Returns information describing the manufacture of the I/O cardinstalled in MIO/EIO slot 1. May include serial number andfirmware revision. "
   USE ""
   INTERACTION " None. "
   OPERATION " Not destructive."
::= { mio1 3 }

-- 1.3.6.1.4.1.11.2.3.9.4.2.1.1.4.3.1.4
mio1-type  OBJECT-TYPE
   SYNTAX      enumerated { eEmpty (1) , eUnknown (2) , eUnSupported (3) , eReadOnlyMemory (4) , eVolatileRandomAccessMemory (5) , eNonVolatileRandomAccessMemory (6) , eFlashMemory (7) , eDiskDrive (8) , eRamRom (9) , eInputPHD (10) , eOutputPHD (11) , eIOCard (12) , eBindingPHD (13) , eSDRandomAccessMemory (14) , eSRandomAccessMemory (15) , eFPMRandomAccessMemory (16) , eEDORandomAccessMemory (17) }
   ACCESS      read-only
   STATUS      optional
   DESCRIPTION "Returns an indication of the type of option installed inMIO/EIO slot 1. See SIMM1-TYPE for an explanation of theenumerations. "
   USE ""
   INTERACTION " None. "
   OPERATION " Not destructive."
::= { mio1 4 }

-- 1.3.6.1.4.1.11.2.3.9.4.2.1.1.4.3.4.2
mio4-model-name  OBJECT-TYPE
   SYNTAX      string
   ACCESS      read-only
   STATUS      optional
   DESCRIPTION "Returns product information identifying the I/O card. Example:XXXX. "
   USE ""
   INTERACTION " None. "
   OPERATION " Not destructive."
::= { mio4 2 }

-- 1.3.6.1.4.1.11.2.3.9.4.2.1.1.4.3.4.3
mio4-manufacturing-info  OBJECT-TYPE
   SYNTAX      string
   ACCESS      read-only
   STATUS      optional
   DESCRIPTION "Returns information describing the manufacture of the I/O cardinstalled in MIO/EIO interface 4. May include serial number andfirmware revision. "
   USE ""
   INTERACTION " None. "
   OPERATION " Not destructive."
::= { mio4 3 }

-- 1.3.6.1.4.1.11.2.3.9.4.2.1.1.4.3.4.4
mio4-type  OBJECT-TYPE
   SYNTAX      enumerated { eEmpty (1) , eUnknown (2) , eUnSupported (3) , eReadOnlyMemory (4) , eVolatileRandomAccessMemory (5) , eNonVolatileRandomAccessMemory (6) , eFlashMemory (7) , eDiskDrive (8) , eRamRom (9) , eInputPHD (10) , eOutputPHD (11) , eIOCard (12) , eBindingPHD (13) , eSDRandomAccessMemory (14) , eSRandomAccessMemory (15) , eFPMRandomAccessMemory (16) , eEDORandomAccessMemory (17) }
   ACCESS      read-only
   STATUS      optional
   DESCRIPTION "Returns an indication of the type of option installed inMIO/EIO interface 4. See SIMM1-TYPE for an explanation of theenumerations. "
   USE ""
   INTERACTION " None. "
   OPERATION " Not destructive."
::= { mio4 4 }

-- 1.3.6.1.4.1.11.2.3.9.4.2.1.1.4.5.2.1
phd2-model  OBJECT-TYPE
   SYNTAX      string
   ACCESS      read-only
   STATUS      optional
   DESCRIPTION "Returns product information identifying PHD device 2. Example:XXXX. "
   USE ""
   INTERACTION " None. "
   OPERATION " Not destructive."
::= { phd2 1 }

-- 1.3.6.1.4.1.11.2.3.9.4.2.1.1.4.5.2.2
phd2-manufacturing-info  OBJECT-TYPE
   SYNTAX      string
   ACCESS      read-only
   STATUS      optional
   DESCRIPTION "Returns information describing the manufacture of PHD 2. Mayinclude serial number and firmware revision. "
   USE ""
   INTERACTION " None. "
   OPERATION " Not destructive."
::= { phd2 2 }

-- 1.3.6.1.4.1.11.2.3.9.4.2.1.1.4.5.2.3
phd2-type  OBJECT-TYPE
   SYNTAX      enumerated { eEmpty (1) , eUnknown (2) , eUnSupported (3) , eReadOnlyMemory (4) , eVolatileRandomAccessMemory (5) , eNonVolatileRandomAccessMemory (6) , eFlashMemory (7) , eDiskDrive (8) , eRamRom (9) , eInputPHD (10) , eOutputPHD (11) , eIOCard (12) , eBindingPHD (13) , eSDRandomAccessMemory (14) , eSRandomAccessMemory (15) , eFPMRandomAccessMemory (16) , eEDORandomAccessMemory (17) }
   ACCESS      read-only
   STATUS      optional
   DESCRIPTION "Returns an indication of the type of option installed in PHDinterface 2. See SIMM1-TYPE for an explanation of theenumerations. "
   USE ""
   INTERACTION " None. "
   OPERATION " Not destructive."
::= { phd2 3 }

-- 1.3.6.1.4.1.11.2.3.9.4.2.1.1.4.5.2.4
phd2-capacity  OBJECT-TYPE
   SYNTAX      integer
   ACCESS      read-only
   STATUS      optional
   DESCRIPTION "Returns an indication of the capacity of the installed option.See SIMM1-CAPACITY for an explanation of the meaning of thevalue of this object. "
   USE ""
   INTERACTION " None. "
   OPERATION " Not destructive."
::= { phd2 4 }

-- 1.3.6.1.4.1.11.2.3.9.4.2.1.1.4.5.2.5
phd2-number-of-options  OBJECT-TYPE
   SYNTAX      integer
   ACCESS      read-only
   STATUS      optional
   DESCRIPTION "This object will return the number of finishing optionssupported by this object. "
   USE ""
   INTERACTION " For each option supported, there will be a corresponding subarray object for the PHD2-OPTIONS-MODEL andPHD2-OPTIONS-DESCRIPTION. "
   OPERATION " Not destructive."
::= { phd2 5 }

-- 1.3.6.1.4.1.11.2.3.9.4.2.1.1.4.5.2.6
phd2-options-model  OBJECT-TYPE
   SYNTAX      string
   ACCESS      read-only
   STATUS      optional
   DESCRIPTION "If the external paper handling device (PHD) supports at leastone (1) finishing option, then this object will exist,otherwise ERROR-UNKNOWN-OBJECT-IDENTIFIER should be returned.Each finishing object supported by the PHD will be representedby a different sub-array element. The sub-array element returnsthe MODEL NUMBER of the finishing option supported, such asBooklet Making or Punching. This may be in the form of C115997or other types of model numbers. "
   USE ""
   INTERACTION " For each sub-array element, there is a corresponding element inthe PHD2-OPTIONS-DESCRIPTION object. See thePHD2-OPTIONS-DESCRIPTION object DESCRIPTION for moreinformation. "
   OPERATION " Not destructive."
::= { phd2 6 }

-- 1.3.6.1.4.1.11.2.3.9.4.2.1.1.4.5.2.7
phd2-options-description  OBJECT-TYPE
   SYNTAX      string
   ACCESS      read-only
   STATUS      optional
   DESCRIPTION "If the external paper handling device (PHD) supports at leastone (1) finishing option, then this object will exist,otherwise ERROR-UNKNOWN-OBJECT-IDENTIFIER should be returned.Each finishing object supported by the PHD will be representedby a different sub-array element. The sub-array element returnsa description of the finishing option supported, such asBooklet Making or Punching. "
   USE ""
   INTERACTION " For each sub-array element, there is a corresponding element inthe PHD2-OPTIONS-MODEL object. See the PHD2-OPTIONS-MODELobject DESCRIPTION for more information. "
   OPERATION " Not destructive."
::= { phd2 7 }

-- 1.3.6.1.4.1.11.2.3.9.4.2.1.1.4.5.3.1
phd3-model  OBJECT-TYPE
   SYNTAX      string
   ACCESS      read-only
   STATUS      optional
   DESCRIPTION "Returns product information identifying PHD device 3. Example:XXXX. "
   USE ""
   INTERACTION " None. "
   OPERATION " Not destructive."
::= { phd3 1 }

-- 1.3.6.1.4.1.11.2.3.9.4.2.1.1.4.5.3.2
phd3-manufacturing-info  OBJECT-TYPE
   SYNTAX      string
   ACCESS      read-only
   STATUS      optional
   DESCRIPTION "Returns information describing the manufacture of PHD 3. Mayinclude serial number and firmware revision. "
   USE ""
   INTERACTION " None. "
   OPERATION " Not destructive."
::= { phd3 2 }

-- 1.3.6.1.4.1.11.2.3.9.4.2.1.1.4.5.3.3
phd3-type  OBJECT-TYPE
   SYNTAX      enumerated { eEmpty (1) , eUnknown (2) , eUnSupported (3) , eReadOnlyMemory (4) , eVolatileRandomAccessMemory (5) , eNonVolatileRandomAccessMemory (6) , eFlashMemory (7) , eDiskDrive (8) , eRamRom (9) , eInputPHD (10) , eOutputPHD (11) , eIOCard (12) , eBindingPHD (13) , eSDRandomAccessMemory (14) , eSRandomAccessMemory (15) , eFPMRandomAccessMemory (16) , eEDORandomAccessMemory (17) }
   ACCESS      read-only
   STATUS      optional
   DESCRIPTION "Returns an indication of the type of option installed in PHDinterface 3. See SIMM1-TYPE for an explanation of theenumerations. "
   USE ""
   INTERACTION " None. "
   OPERATION " Not destructive."
::= { phd3 3 }

-- 1.3.6.1.4.1.11.2.3.9.4.2.1.1.4.5.3.4
phd3-capacity  OBJECT-TYPE
   SYNTAX      integer
   ACCESS      read-only
   STATUS      optional
   DESCRIPTION "Returns an indication of the capacity of the installed option.See SIMM1-CAPACITY for an explanation of the meaning of thevalue of this object. "
   USE ""
   INTERACTION " None. "
   OPERATION " Not destructive."
::= { phd3 4 }

-- 1.3.6.1.4.1.11.2.3.9.4.2.1.1.4.5.3.5
phd3-number-of-options  OBJECT-TYPE
   SYNTAX      integer
   ACCESS      read-only
   STATUS      optional
   DESCRIPTION "This object will return the number of finishing optionssupported by this object. "
   USE ""
   INTERACTION " For each option supported, there will be a corresponding subarray object for the PHD3-OPTIONS-MODEL andPHD3-OPTIONS-DESCRIPTION. "
   OPERATION " Not destructive."
::= { phd3 5 }

-- 1.3.6.1.4.1.11.2.3.9.4.2.1.1.4.5.3.6
phd3-options-model  OBJECT-TYPE
   SYNTAX      string
   ACCESS      read-only
   STATUS      optional
   DESCRIPTION "If the external paper handling device (PHD) supports at leastone (1) finishing option, then this object will exist,otherwise ERROR-UNKNOWN-OBJECT-IDENTIFIER should be returned.Each finishing object supported by the PHD will be representedby a different sub-array element. The sub-array element returnsthe MODEL NUMBER of the finishing option supported, such asBooklet Making or Punching. This may be in the form of C115997or other types of model numbers. "
   USE ""
   INTERACTION " For each sub-array element, there is a corresponding element inthe PHD3-OPTIONS-DESCRIPTION object. See thePHD3-OPTIONS-DESCRIPTION object DESCRIPTION for moreinformation. "
   OPERATION " Not destructive."
::= { phd3 6 }

-- 1.3.6.1.4.1.11.2.3.9.4.2.1.1.4.5.3.7
phd3-options-description  OBJECT-TYPE
   SYNTAX      string
   ACCESS      read-only
   STATUS      optional
   DESCRIPTION "If the external paper handling device (PHD) supports at leastone (1) finishing option, then this object will exist,otherwise ERROR-UNKNOWN-OBJECT-IDENTIFIER should be returned.Each finishing object supported by the PHD will be representedby a different sub-array element. The sub-array element returnsa description of the finishing option supported, such asBooklet Making or Punching. "
   USE ""
   INTERACTION " For each sub-array element, there is a corresponding element inthe PHD3-OPTIONS-MODEL object. See the PHD3-OPTIONS-MODELobject DESCRIPTION for more information. "
   OPERATION " Not destructive."
::= { phd3 7 }

-- 1.3.6.1.4.1.11.2.3.9.4.2.1.1.4.6.1.4
web-proxy-config-enable  OBJECT-TYPE
   SYNTAX      enumerated { eOff (0) , eOn (1) }
   ACCESS      read-only
   STATUS      optional
   DESCRIPTION "This object is a binary enumeration which the peripheral usesto inform the JetDirect card that the Jet-Direct card embeddedweb server should display the web proxy configuration settings.The Jet Direct card web server will display the if and only ifthis object is both implemented and set to eOn. A peripheralmay implement this object in order to have another host, like aJetDirect card, include a reference to the peripheral's webcontent. The peripheral will read the proxy configuration usingthe XIP2 sysInfo Get methods. "
   USE ""
   INTERACTION " None. "
   OPERATION " Not destructive."
::= { settings-web-server 4 }

-- 1.3.6.1.4.1.11.2.3.9.4.2.1.1.4.6.1.5
ews-request-control-panel-supplies-status  OBJECT-TYPE
   SYNTAX      enumerated { eFalse (1) , eTrue (2) }
   ACCESS      read-write
   STATUS      optional
   DESCRIPTION "System variable EWS_REQUEST_CONTROL_PANEL_SUPPPLIES_STATUSrequires a PML interface so that WJA can directly access itwithout needing EWS support for that. "
   USE ""
   INTERACTION " The value of this object can be changed through EWS. "
   OPERATION " Not Destructive."
::= { settings-web-server 5 }

-- 1.3.6.1.4.1.11.2.3.9.4.2.1.1.4.8.2
fih-extra-pulses-feature  OBJECT-TYPE
   SYNTAX      enumerated { eDisable (1) , eEnable (2) }
   ACCESS      read-write
   STATUS      optional
   DESCRIPTION "This object allows one to get/set the setting of the FIH EXTRAPULSES FEATURE item. This either turns the feature on or offbased on customer requirement. "
   USE ""
   INTERACTION " None "
   OPERATION " Not destructive."
::= { foreign-interface 2 }

-- 1.3.6.1.4.1.11.2.3.9.4.2.1.1.4.9.1
usb-host-supported  OBJECT-TYPE
   SYNTAX      enumerated { eFalse (1) , eTrue (2) }
   ACCESS      read-only
   STATUS      optional
   DESCRIPTION "The USB Host protocol is supported by the device when the valuereturned is eTrue. The USB Host protocol is not supported whenthe value returned is eFalse. "
   USE ""
   INTERACTION " None. "
   OPERATION " Not destructive."
::= { usb-interface 1 }

-- 1.3.6.1.4.1.11.2.3.9.4.2.1.1.4.9.2.1
usb-serial-number  OBJECT-TYPE
   SYNTAX      string
   ACCESS      read-only
   STATUS      optional
   DESCRIPTION "Returns the serial number of a connected USB device as definedin the Standard Device Descriptor of the Universal Serial BusSpecification Version 2.0. "
   USE ""
   INTERACTION " None. "
   OPERATION " Not destructive."
::= { usb 1 }

-- 1.3.6.1.4.1.11.2.3.9.4.2.1.1.4.9.2.2
usb-manufacturer-name  OBJECT-TYPE
   SYNTAX      string
   ACCESS      read-only
   STATUS      optional
   DESCRIPTION "Returns the description of the manufacturer of a connected USBdevice as defined in the Standard Device Descriptor of theUniversal Serial Bus Specification Version 2.0. "
   USE ""
   INTERACTION " None. "
   OPERATION " Not destructive."
::= { usb 2 }

-- 1.3.6.1.4.1.11.2.3.9.4.2.1.1.4.9.2.3
usb-product-description  OBJECT-TYPE
   SYNTAX      string
   ACCESS      read-only
   STATUS      optional
   DESCRIPTION "Returns the product description of a connected USB device asdefined in the Standard Device Descriptor of the UniversalSerial Bus Specification Version 2.0. "
   USE ""
   INTERACTION " None. "
   OPERATION " Not destructive."
::= { usb 3 }

-- 1.3.6.1.4.1.11.2.3.9.4.2.1.1.4.9.2.4
usb-vendor-id  OBJECT-TYPE
   SYNTAX      integer
   ACCESS      read-only
   STATUS      optional
   DESCRIPTION "Returns the Vendor ID of a connected USB device as defined inthe Standard Device Descriptor of the Universal Serial BusSpecification Version 2.0. The value will be in the range0..65535. "
   USE ""
   INTERACTION " None. "
   OPERATION " Not destructive."
::= { usb 4 }

-- 1.3.6.1.4.1.11.2.3.9.4.2.1.1.4.9.2.5
usb-product-id  OBJECT-TYPE
   SYNTAX      integer
   ACCESS      read-only
   STATUS      optional
   DESCRIPTION "Returns the Product ID of a connected USB device as defined inthe Standard Device Descriptor of the Universal Serial BusSpecification Version 2.0. The value will be in the range0..65535. "
   USE ""
   INTERACTION " None. "
   OPERATION " Not destructive."
::= { usb 5 }

-- 1.3.6.1.4.1.11.2.3.9.4.2.1.1.4.9.2.6
usb-device-kind  OBJECT-TYPE
   SYNTAX      enumerated { eUSBStorageDevice (1) , eUSBNonStorageDevice (2) , eUSBCompositeDevice (3) , eUSBUnsupportedDevice (4) }
   ACCESS      read-only
   STATUS      optional
   DESCRIPTION "The USB-DEVICE-KIND object classifies a USB device into one offour broad categories: \eUSBStorageDevice(1): The USB device is strictly a devicefor storing data. \eUSBNonStorageDevice(2): The USB device has no storagecapability (e.g., a card reader). \eUSBCompositeDevice(3): The USB device has storagecapability and additional functionality normally notassociated with a storage device. \eUSBUnsupportedDevice(4): The USB device was detected, but nodriver exists for the device or the device draws more currentthan allowed. \ "
   USE ""
   INTERACTION " None. "
   OPERATION " Not destructive."
::= { usb 6 }

-- 1.3.6.1.4.1.11.2.3.9.4.2.1.1.4.9.2.7
usb-driver-name  OBJECT-TYPE
   SYNTAX      string
   ACCESS      read-only
   STATUS      optional
   DESCRIPTION "Returns the name of the low-level USB driver supporting thisdevice. "
   USE ""
   INTERACTION " None. "
   OPERATION " Not destructive."
::= { usb 7 }

-- 1.3.6.1.4.1.11.2.3.9.4.2.1.1.5.2
print-internal-page  OBJECT-TYPE
   SYNTAX      enumerated { eNotPrintingAnInternalPage (1) , ePrintingAnUnknownInternalPage (2) , eDeviceDemoPage1ConfigurationPage (3) , eDeviceDemoPage2 (4) , eDeviceDemoPage3SpeedDialPage (5) , eDeviceDemoPage4ExtensiveDeviceInformation (6) , eDeviceDemoPage5ErrorLog (7) , eDeviceDemoPage6FileSystemDirectoryListing (8) , eDeviceDemoPage7MenuMap (9) , eDeviceUsagePage (10) , eDeviceDemoPage8BlockFaxList (11) , eDeviceDemoPage9FaxLogReport (12) , eServicePage (13) , eServicePageWarningLog (14) , eServicePageJamHistory (15) , eServicePageServiceSummary (16) , eServicePageServiceSettings (17) , eServicePagePM (18) , ePrintUsagePage (100) , eSuppliesPage (101) , eMediaPathUsagePage (102) , eSuppliesUsagePage (103) , eDeviceADFAdjustmentPages (250) , eDeviceColorRegistrationPage (251) , eDeviceAutoCleaningPage (252) , eDeviceCleaningPage (253) , eDevicePaperPathTest (254) , eDevicePageRegistrationPage (255) , ePrintQualityPages (256) , eHighVoltageTestPage (257) , eColorPaletteRGBPage (258) , eColorPaletteCMYKPage (259) , eDevicePageDiagnosticsPage (260) , eDevicePageStoredJobsPage (261) , eSWActivatedRibSmearCleanerPage (262) , eSWActivatedPickTireCleanerPage (263) , eXPSErrorPage (264) , ePCLDemoPage1ConfigurationPage (300) , ePCLDemoPage2 (301) , ePCLFontList1 (350) , ePCLFontList2 (352) , ePCLXLFontList (353) , ePostScriptDemoPage1ConfigurationPage (400) , ePostScriptDemoPage2 (401) , ePostScriptFontList1 (450) , ePostScriptFontList2 (451) , eEscPDemoPage1ConfigurationPage (500) , eEscPDemoPage2 (501) , eEscPFontList1 (550) , eEscPFontList2 (551) , eEpsonDemoPage1ConfigurationPage (600) , eEpsonDemoPage2 (601) , eEpsonFontList1 (650) , eEpsonFontList2 (651) , eIPDSDemoPage1ConfigurationPage (700) , eIPDSDemoPage2 (701) , eIPDSFontList1 (750) , eIPDSFontList2 (751) , eHPGLDemoPage1ConfigurationPage (800) , eHPGLDemoPage2 (801) , eHPGLFontList1 (850) , eHPGLFontList2 (851) , eHPGL2DemoPage1ConfigurationPage (900) , eHPGL2DemoPage2 (901) , eHPGL2FontList1 (950) , eHPGL2FontList2 (951) , eMarkingAgentTestPattern (1000) , eCalibrationNormalPage (1100) , eCalibrationPhotoPage (1101) , eColorCalibrationPage (1102) , eColorCalConfirmPage (1103) , ePenAlignmentPage (1150) , ePenAlignmentVerificationPage (1151) , ePrintSimplifiedAlignmentPage (1152) , eNetworkConfigPage (1200) , eNetworkConfigMultiLangPage (1201) , eWirelessNetworkTestPage (1202) , eFaxSelfTestShort (1300) , eFaxSelfTestPage (1301) , eFaxSelfTestExtended (1302) , ePDFEaterErrorPage (1303) , eFaxActivityLogPage (1304) , eFaxCallReportPage (1305) , eFaxCallReportOnEventPage (1306) , eBillingReportPage (1307) , eSpeedDialListReportPage (1308) , eBlockedFaxListReportPage (1309) , eT30TracerReportPage (1310) , eT30TracerReportOnEventPage (1311) , eDeviceShowMeHowPageClearJams (1400) , eDeviceShowMeHowPageLoadTrays (1401) , eDeviceShowMeHowPageLoadSpecialMedia (1402) , eDeviceShowMeHowPagePrintBothSides (1403) , eDeviceShowMeHowPageSupportedPaper (1404) , eDeviceShowMeHowPageMoreHelp (1405) , eDeviceShowMeHowHelpGuide (1406) , eAutomaticLinefeedCalibration (1407) , eAutomaticColorCalibration (1408) , ePrintQualityDiagnosticPage (1409) , eCurrentSettingsPage (1410) , eDeviceShowMeHowPageLoadMedia4x6 (1411) , eColorUsageLog (1412) }
   ACCESS      read-write , trappable
   STATUS      optional
   DESCRIPTION "Writing this object to a value other thaneNotPrintingAnInternalPage causes the device to attempt toprint an internally generated page. Reading this objectprovides an indication what internally generated page iscurrently being printed, if any. The actual page is devicespecific. Some devices may support continuously printing aninternally generated page. Setting this object toeNotPrintingAnInternalPage terminates continuously printinginternally generated pages. An internally generated page maynot be allowed to be printed at any arbitrary time; under whatconditions it will succeed or fail is device specific. If thedevice supports the requested page, but can not start printingthe page when requested, the device will respond with&lt;ErrorActionCanNotBePerformedNow&gt;. RECOMMENDATION: If thedevice is ready (i.e. the NOT-READY-PRINTER object does notcontain any items, except maybe being off-line) and is idle(i.e. the NOT-IDLE object does not contain any items), thisrequest should always succeed. This provides a mechanism fordriver writers to always determine if the action will succeedor not. "
   USE ""
   INTERACTION " None. "
   OPERATION " Setting this object identifier may cause the device topermanently stop accepting print jobs. The actual behavior isdevice specific."
::= { test 2 }

-- 1.3.6.1.4.1.11.2.3.9.4.2.1.1.5.7
engine-self-diagnostic  OBJECT-TYPE
   SYNTAX      binary
   ACCESS      read-only
   STATUS      optional
   DESCRIPTION "The ENGINE-SELF-DIAGNOSTIC object reveals current enginefailures; it returns a binary string of two-byte motor, clutch,solenoid, and sensor failure codes. "
   USE ""
   INTERACTION " None. "
   OPERATION " Not destructive."
::= { test 7 }

-- 1.3.6.1.4.1.11.2.3.9.4.2.1.1.5.8
engine-parameter  OBJECT-TYPE
   SYNTAX      binary
   ACCESS      read-only
   STATUS      optional
   DESCRIPTION "The ENGINE-PARAMETER object returns a device specific set ofengine parameters as a binary string of byte values. It will benecessary to have a decoder for each engine to interpret thedata. "
   USE ""
   INTERACTION " None. "
   OPERATION " Not destructive."
::= { test 8 }

-- 1.3.6.1.4.1.11.2.3.9.4.2.1.1.6.1.1
clearable-warning  OBJECT-TYPE
   SYNTAX      enumerated { eOff (1) , eOn (2) , eJob (3) }
   ACCESS      read-write
   STATUS      optional
   DESCRIPTION "Returns or controls how the device will track clearablewarnings. A clearable warning indicates a transient event inthe device. The device will continue after the transient eventoccurs. If CLEARABLE-WARNING is eOff, the device does not trackclearable warnings. If CLEARABLE-WARNING is eOn, all clearablewarnings will be tracked until cleared (acknowledged). IfCLEARABLE-WARNING is eJob, a clearable warning generated due toan event that occurs because of the print job being processedwill be automatically cleared when the device has finishedprocessing the job. Example clearable warning events includethe device altering resolution or page protection due to memoryconstraints. The POS will document what transient events aretreated as clearable warnings. "
   USE ""
   INTERACTION " May not be settable if NOT-IDLE contains the cProcessingPDLitem. "
   OPERATION " Not destructive."
::= { settings-job 1 }

-- 1.3.6.1.4.1.11.2.3.9.4.2.1.1.6.1.10
hold-job-timeout  OBJECT-TYPE
   SYNTAX      integer
   ACCESS      read-write
   STATUS      optional
   DESCRIPTION "The time, in minutes, that the printer will wait beforeautomatically deleting a held job. This allows the printer toautomatically clean up jobs that have been forgotten (held butnever released). "
   USE ""
   INTERACTION " None. "
   OPERATION " Not destructive."
::= { settings-job 10 }

-- 1.3.6.1.4.1.11.2.3.9.4.2.1.1.6.1.2
cancel-job  OBJECT-TYPE
   SYNTAX      integer
   ACCESS      read-write , trappable
   STATUS      optional
   DESCRIPTION "Cancels the print job whose ID matches the value written to theCANCEL-JOB object. The host first learns the job ID using theCURRENT-JOB-PARSING-ID command. If the printer has completelyprocessed the job, the printer responds with&lt;ErrorInvalidOrUnsupportedValue&gt;. If the value of theCURRENT-JOB-PARSING-ID is smaller than the value written to theCANCEL-JOB object, then the printer responds with&lt;ErrorInvalidOrUnsupportedValue&gt;. When read, returns the valueof the last job ID what was canceled, or -1 to indicate no jobhas been canceled. "
   USE ""
   INTERACTION " May not be settable if NOT-IDLE contains the cProcessingPDLitem. "
   OPERATION " Not destructive."
::= { settings-job 2 }

-- 1.3.6.1.4.1.11.2.3.9.4.2.1.1.6.1.3
job-info-change-id  OBJECT-TYPE
   SYNTAX      binary
   ACCESS      read-only , trappable
   STATUS      optional
   DESCRIPTION "Returns the current value of an object in the job-info sub-treewhose value has changed. Define the object identifier for theobject whose value has changed asjob-info.required-field.optional-field.job-id. job-inforepresents the OID prefix of all objects in the job-infosub-tree. Required-field represents the OID field value thatfollows the job-info prefix. Since some objects in the job-infosub-tree have two OID fields between the job-info prefix andthe job-id, the optional-field represents the OID field betweenthe required-field and the job-id field, if present. Using thisdefinition, the format for the JOB-INFO-CHANGE-ID binary valuecan be described as follows: \\Bytes 0-3 : required-field \\Bytes 4-7 : optional-field, or all zeros if there \\is no optional field \\Bytes 8-11: Job ID. \\Bytes 12-n : The value of the object job-info.required-field.optional-field.job-id. \\All multi-byte values stored in Motorola (big-endian) format,where the most significant byte occurs first. "
   USE ""
   INTERACTION " None. "
   OPERATION " Not destructive."
::= { settings-job 3 }

-- 1.3.6.1.4.1.11.2.3.9.4.2.1.1.6.2.1.1
current-job-parsing-id  OBJECT-TYPE
   SYNTAX      integer
   ACCESS      read-only , trappable
   STATUS      optional
   DESCRIPTION "Contains the printer assigned job identification for the jobcurrently being processed by the processing PDL sub-system. Thejob ID is a monotonically increasing number. The job ID may bereset to zero at power-up and may roll over to zero afterreaching some maximum value. "
   USE ""
   INTERACTION "  "
   OPERATION " Not destructive."
::= { job-being-parsed 1 }

-- 1.3.6.1.4.1.11.2.3.9.4.2.1.1.6.5.1
job-info-name1  OBJECT-TYPE
   SYNTAX      string
   ACCESS      read-only
   STATUS      optional
   DESCRIPTION "Contains the first part of this print job's name. The last OIDfield for this dynamic object contains the job ID. "
   USE ""
   INTERACTION " None. "
   OPERATION " Not destructive."
job-info 1

-- 1.3.6.1.4.1.11.2.3.9.4.2.1.1.6.5.10
job-info-stage  OBJECT-TYPE
   SYNTAX      collection { cSourceSubsystem (0) , cProcessingSubsystem (1) , cDestinationSubsystem (2) }
   ACCESS      read-only
   STATUS      optional
   DESCRIPTION "Indicates what printer sub-systems are currently processingthis print job. The last OID field for this dynamic objectcontains the job ID. cSourceSubsystem - some of the job is inthe printer I/O subsystem. cProcessingSubsystem - some of thejob is in the printer imaging processing subsystem.cDestinationSubsystem - some of the job is being printed. "
   USE ""
   INTERACTION " None. "
   OPERATION " Not destructive."
::= { job-info 10 }

-- 1.3.6.1.4.1.11.2.3.9.4.2.1.1.6.5.11
job-info-io-source  OBJECT-TYPE
   SYNTAX      integer
   ACCESS      read-only
   STATUS      optional
   DESCRIPTION "Indicates which I/O source, the print job was received over.The value maps to port numbering scheme supported in theDEVICE/SOURCE-SUBSYSTEM/IO/PORTS sub-tree. "
   USE ""
   INTERACTION " None. "
   OPERATION " Not destructive."
::= { job-info 11 }

-- 1.3.6.1.4.1.11.2.3.9.4.2.1.1.6.5.12
job-info-pages-processed  OBJECT-TYPE
   SYNTAX      integer
   ACCESS      read-only
   STATUS      optional
   DESCRIPTION "Indicates the number of pages processed by the processingsubsystem. If neither the cSourceSubsystem or thecProcessingSubsystem items are in the associated JOB-INFO-STAGEobject, then this object contains the total number of pagesprocessed for this job. The last OID field for this dynamicobject contains the job ID. "
   USE ""
   INTERACTION " None. "
   OPERATION " Not destructive."
::= { job-info 12 }

-- 1.3.6.1.4.1.11.2.3.9.4.2.1.1.6.5.13
job-info-pages-printed  OBJECT-TYPE
   SYNTAX      integer
   ACCESS      read-only , trappable
   STATUS      optional
   DESCRIPTION "Indicates the number of pages printed by the destinationsubsystem. If none of the cSourceSubsystem,cProcessingSubsystem or cDestinationSubsystem items are in theassociated JOB-INFO-STAGE object, then this object contains thetotal number of pages printed for this job. This value mayincrease by two each time for duplex jobs. The last OID fieldfor this dynamic object contains the job ID. "
   USE ""
   INTERACTION " None. "
   OPERATION " Not destructive."
::= { job-info 13 }

-- 1.3.6.1.4.1.11.2.3.9.4.2.1.1.6.5.14
job-info-size  OBJECT-TYPE
   SYNTAX      integer
   ACCESS      read-only
   STATUS      optional
   DESCRIPTION "Indicates the number of bytes of data processed by theprocessing subsystem. If neither of the cSourceSubsystem orcProcessingSubsystem items are in the associated JOB-INFO-STAGEobject, then this object contains the size of this job, inbytes. The last OID field for this dynamic object contains thejob ID. "
   USE ""
   INTERACTION " None. "
   OPERATION " Not destructive."
::= { job-info 14 }

-- 1.3.6.1.4.1.11.2.3.9.4.2.1.1.6.5.15
job-info-state  OBJECT-TYPE
   SYNTAX      enumerated { eAborted (3) , eWaitingForResources (4) , ePrinted (5) , eRetained (6) , eTerminating (7) , eInterrupted (8) , ePaused (9) , eCancelled (10) , eProcessing (11) , eScanning (12) , eSending (13) , eStored (14) }
   ACCESS      read-only , trappable
   STATUS      optional
   DESCRIPTION "Indicates the state of the job. The last OID field for thisdynamic object contains the job ID. \\eAborted - the print job was aborted. \\eWaitingForResources - the print job requires resourcesthat are not currently available. Example resourcesthat can cause the job to wait include the print engineor PDL processor being unavailable. The print enginecould be unavailable due to paper out, paper jam,staple out, stapler jam, marking agent low, output binfull, etc. The PDL processor could be unavailable dueto an off-line condition. Each printer specific objectspecification should state which conditions cause a jobto be waiting for resources and also state whichobjects can be retrieved by an application to determinethe exact cause of a resource being unavailable. \\ePrinted - the job has printed. The related JOB-INFO-OUTCOME object indicates if any problems wereencountered while the job was processed. \\eRetained - the job can be reprinted. \\eTerminating - the job was aborted or cancelled and iscurrently is terminating. \\eInterrupted - the job has been interrupted. The job can becontinued. \\ePaused - the job has been paused. The job can becontinuted. \\eCancelled - the job has been cancelled. \\eProcessing - the job is currently being printed normally.eStored - The job is stored on the device and can be retrievedand printed at a later point in time. "
   USE ""
   INTERACTION " None. "
   OPERATION " Not destructive."
::= { job-info 15 }

-- 1.3.6.1.4.1.11.2.3.9.4.2.1.1.6.5.19
job-info-outcome  OBJECT-TYPE
   SYNTAX      enumerated { eOk (3) , eWarningsEncountered (4) , eErrorsEncountered (5) }
   ACCESS      read-only
   STATUS      optional
   DESCRIPTION "Indicates if any warning or error conditions were encounteredwhile processing the assoicated job. The last OID field forthis dynamic object contains the job ID. "
   USE ""
   INTERACTION " None. "
   OPERATION " Not destructive."
::= { job-info 19 }

-- 1.3.6.1.4.1.11.2.3.9.4.2.1.1.6.5.2
job-info-name2  OBJECT-TYPE
   SYNTAX      string
   ACCESS      read-only
   STATUS      optional
   DESCRIPTION "Contains the second part of this print job's name. The last OIDfield for this dynamic object contains the job ID. "
   USE ""
   INTERACTION " None. "
   OPERATION " Not destructive."
job-info 2

-- 1.3.6.1.4.1.11.2.3.9.4.2.1.1.6.5.20
job-info-outbins-used  OBJECT-TYPE
   SYNTAX      collection { cOutbin1 (0) , cOutbin2 (1) , cOutbin3 (2) , cOutbin4 (3) , cOutbin5 (4) , cOutbin6 (5) , cOutbin7 (6) , cOutbin8 (7) , cOutbin9 (8) , cOutbin10 (9) , cOutbin11 (10) , cOutbin12 (11) , cOutbin13 (12) , cOutbin14 (13) , cOutbin15 (14) , cOutbin16 (15) , cOutbin17 (16) }
   ACCESS      read-only
   STATUS      optional
   DESCRIPTION "Indicates which output bins this job has delivered printedpages to. The last OID field for this dynamic object containsthe job ID. "
   USE ""
   INTERACTION " None. "
   OPERATION " Not destructive."
::= { job-info 20 }

-- 1.3.6.1.4.1.11.2.3.9.4.2.1.1.6.5.22
job-info-physical-outbins-used  OBJECT-TYPE
   SYNTAX      collection { cOutbin1 (0) , cOutbin2 (1) , cOutbin3 (2) , cOutbin4 (3) , cOutbin5 (4) , cOutbin6 (5) , cOutbin7 (6) , cOutbin8 (7) , cOutbin9 (8) , cOutbin10 (9) , cOutbin11 (10) , cOutbin12 (11) , cOutbin13 (12) , cOutbin14 (13) , cOutbin15 (14) , cOutbin16 (15) , cOutbin17 (16) }
   ACCESS      read-only
   STATUS      optional
   DESCRIPTION "Indicates which physical output bins this job has deliveredprinted pages to. The last OID field for this dynamic objectcontains the job ID. "
   USE ""
   INTERACTION " None. "
   OPERATION " Not destructive."
::= { job-info 22 }

-- 1.3.6.1.4.1.11.2.3.9.4.2.1.1.6.5.23.1
job-info-attr-1  OBJECT-TYPE
   SYNTAX      binary
   ACCESS      read-only
   STATUS      optional
   DESCRIPTION "Returns the value that was set in PJL via the SET JOBATTR=command. Attribute objects are saved sequentially, startingwith 1, after the start of a job. If more attributes are setthan there are objects to store them, the excess JOBATTR valuesare ignored. If the corresponding SET JOBATTR= command has notbeen received when a get is done for this object, a status of&lt;ErrorUnknownObjectIdentifier&gt; will be returned. "
   USE ""
   INTERACTION " None. "
   OPERATION " Not destructive."
::= { job-info-attribute 1 }

-- 1.3.6.1.4.1.11.2.3.9.4.2.1.1.6.5.23.10
job-info-attr-10  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 10 }

-- 1.3.6.1.4.1.11.2.3.9.4.2.1.1.6.5.23.11
job-info-attr-11  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 11 }

-- 1.3.6.1.4.1.11.2.3.9.4.2.1.1.6.5.23.12
job-info-attr-12  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 12 }

-- 1.3.6.1.4.1.11.2.3.9.4.2.1.1.6.5.23.13
job-info-attr-13  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 13 }

-- 1.3.6.1.4.1.11.2.3.9.4.2.1.1.6.5.23.14
job-info-attr-14  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 14 }

-- 1.3.6.1.4.1.11.2.3.9.4.2.1.1.6.5.23.15
job-info-attr-15  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 15 }

-- 1.3.6.1.4.1.11.2.3.9.4.2.1.1.6.5.23.16
job-info-attr-16  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 16 }

-- 1.3.6.1.4.1.11.2.3.9.4.2.1.1.6.5.23.2
job-info-attr-2  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 2 }

-- 1.3.6.1.4.1.11.2.3.9.4.2.1.1.6.5.23.3
job-info-attr-3  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 3 }

-- 1.3.6.1.4.1.11.2.3.9.4.2.1.1.6.5.23.4
job-info-attr-4  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 4 }

-- 1.3.6.1.4.1.11.2.3.9.4.2.1.1.6.5.23.5
job-info-attr-5  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 5 }

-- 1.3.6.1.4.1.11.2.3.9.4.2.1.1.6.5.23.6
job-info-attr-6  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 6 }

-- 1.3.6.1.4.1.11.2.3.9.4.2.1.1.6.5.23.7
job-info-attr-7  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 7 }

-- 1.3.6.1.4.1.11.2.3.9.4.2.1.1.6.5.23.8
job-info-attr-8  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 8 }

-- 1.3.6.1.4.1.11.2.3.9.4.2.1.1.6.5.23.9
job-info-attr-9  OBJECT-TYPE
   SYNTAX      binary
   ACCESS      read-only
   STATUS      optional
   DESCRIPTION "Returns the value that was set in PJL via the SET JOBATTR=command. See JOB-INFO-ATTR-1 for details. "
   USE ""
   INTERACTION " None. "
   OPERATION " Not destructive."
::= { job-info-attribute 9 }

-- 1.3.6.1.4.1.11.2.3.9.4.2.1.1.6.5.24
job-info-requested-originals  OBJECT-TYPE
   SYNTAX      integer
   ACCESS      read-only
   STATUS      optional
   DESCRIPTION "The number of requested collated copies. The value was suppliedwith the job via PJL QTY variable, the PostScript Collate andNumCopies entries in the page device dictionary, or via someother mechansim. "
   USE ""
   INTERACTION " This object only exists after the job is identified as acollated multi-copy job. "
   OPERATION " Not destructive."
::= { job-info 24 }

-- 1.3.6.1.4.1.11.2.3.9.4.2.1.1.6.5.25
job-info-page-count-current-original  OBJECT-TYPE
   SYNTAX      integer
   ACCESS      read-only
   STATUS      optional
   DESCRIPTION "The page number being printed within the current copy of acollated multi-copy job. This value changes when thejob-info-pages-printed changes. The job-info-pages-printedindicates the total number of pages printed in the job, whilethis object indicates the number of pages printed for this copyof a collated multi-copy job. "
   USE ""
   INTERACTION " This object only exists after the job is identified as acollated multi-copy job. "
   OPERATION " Not destructive."
::= { job-info 25 }

-- 1.3.6.1.4.1.11.2.3.9.4.2.1.1.6.5.26
job-info-pages-in-original  OBJECT-TYPE
   SYNTAX      integer
   ACCESS      read-only
   STATUS      optional
   DESCRIPTION "Number of pages in a single copy of a collated multi-copy job. "
   USE "  "
   INTERACTION " This object does not exist until the printer knows the numberof pages per copy in a collated multi-copy job. "
   OPERATION " Not destructive."
::= { job-info 26 }

-- 1.3.6.1.4.1.11.2.3.9.4.2.1.1.6.5.27
job-info-printed-originals  OBJECT-TYPE
   SYNTAX      integer
   ACCESS      read-only
   STATUS      optional
   DESCRIPTION "Number of collated copies completely printed and delivered tothe output bin at time of query. "
   USE ""
   INTERACTION " This object only exists after the job is identified as acollated multi-copy job. "
   OPERATION " Not destructive."
::= { job-info 27 }

-- 1.3.6.1.4.1.11.2.3.9.4.2.1.1.6.5.28.1
job-info-accounting-media-size  OBJECT-TYPE
   SYNTAX      enumerated { eUSExecutive (1) , eUSLetter (2) , eUSLegal (3) , eFoolscap (10) , eLedger (11) , eROC16K (17) , eJISExecutive (18) , eROC8K (19) , eISOandJISA6 (24) , eISOandJISA5 (25) , eISOandJISA4 (26) , eISOandJISA3 (27) , ePRC8K270X390 (33) , ePRC16K195X270 (34) , ePRC8K260X368 (35) , eJISB6 (44) , eJISB5 (45) , eJISB4 (46) , eISOB5 (65) , eJapansePostcardSingle (71) , eJapansePostcardDouble (72) , eISOA6Postcard (73) , eIndexCard4x6 (74) , eIndexCard5x8 (75) , ePhoto4x6 (76) , eJapanesePostcardWithTab (77) , eMonarch (80) , eCommercial10 (81) , ePRC16K184X260 (89) , eInternationalDL (90) , eInternationalC5 (91) , eInternationalC6 (92) , eInternationalB5 (100) , eCustom (101) , eUSEnvelopeA2 (109) , eJapanseEnvLong3 (110) , eJapanseEnvLong4 (111) , eUSExecutiveR (257) , eUSLetterR (258) , eROC16KR (273) , eISOandJISA6R (280) , eISOandJISA5R (281) , eISOandJISA4R (282) , eJISBR6R (300) , eJISB5R (301) , eAnyCustomSize (32764) , eAnySize (32765) , eCustomRoll (32766) , eUnknownMediaSize (32767) }
   ACCESS      read-only
   STATUS      optional
   DESCRIPTION "Contains the media size of the printed job. The media size ofthe first page will decide the media size of the entire job.The return value of this object will only be valid when theprinter finishes printing the entire job. "
   USE ""
   INTERACTION " None. "
   OPERATION " Not destructive."
job-info-accounting   1

-- 1.3.6.1.4.1.11.2.3.9.4.2.1.1.6.5.28.10
job-info-accounting-cyan-dots  OBJECT-TYPE
   SYNTAX      integer
   ACCESS      read-only
   STATUS      optional
   DESCRIPTION "Contains the total number of cyan pixels used in a particularjob. "
   USE ""
   INTERACTION " None. "
   OPERATION " Not destructive."
::= { job-info-accounting 10 }

-- 1.3.6.1.4.1.11.2.3.9.4.2.1.1.6.5.28.11
job-info-accounting-magenta-dots  OBJECT-TYPE
   SYNTAX      integer
   ACCESS      read-only
   STATUS      optional
   DESCRIPTION "Contains the total number of magenta pixels used in aparticular job. "
   USE ""
   INTERACTION " None. "
   OPERATION " Not destructive."
::= { job-info-accounting 11 }

-- 1.3.6.1.4.1.11.2.3.9.4.2.1.1.6.5.28.14
job-info-accounting-job-type  OBJECT-TYPE
   SYNTAX      enumerated { ePrintJob (1) , eIPPJob (2) , eCopyJob (3) , eCopyInterruptJob (4) , eJetSendJob (5) , eInternalPage (6) , eCleaningPage (7) , eAutoCleaningPage (8) , eDigitalSendJob (9) , eWebPrintJob (10) , eFaxPrintJob (11) , eRetrievedJob (12) , ePhotoCardPrintJob (13) , eUnknownJob (1000) }
   ACCESS      read-only
   STATUS      optional
   DESCRIPTION "Keeps track of what type of job is processed.  "
   USE ""
   INTERACTION " None. "
   OPERATION " Not destructive."
::= { job-info-accounting 14 }

-- 1.3.6.1.4.1.11.2.3.9.4.2.1.1.6.5.28.2
job-info-accounting-media-type  OBJECT-TYPE
   SYNTAX      enumerated { eUnknownMedia (1) , eStandardType (2) , ePreprinted (3) , eLetterhead (4) , eTransparency (5) , ePrepunched (6) , eLabels (7) , eBond (8) , eRecycled (9) , eColored (10) , eCardStock (11) , eRough (12) , eVellum (13) , eHeavy (14) , eGloss (15) , eUserType1 (16) , eUserType2 (17) , eUserType3 (18) , eUserType4 (19) , eUserType5 (20) , ePhotoGlossy (24) , ePhotoQualityGlossy (25) , ePhotoQualityMatte (26) , eEverydayPhotoGlossy (27) , eEverydayPhotoMatte (28) , ePremiumInkjet (29) , ePremiumInkjetHeavy (30) , eBrochureGlossy (31) , eBrochureMatte (32) , ePremiumPhotoGlossy (33) , ePremiumPlussPhotoGlossy (34) , ePremiumPlusPhotoMatte (35) , eColorfastPhotoGlossy (36) , ePremiumTransparency (37) , ePremiumPlusTranparency (38) , eNHPHeavyGloss (39) , eExtraHeavy (40) , eHighGlossImages (41) , eIntermediate (42) , eTab (43) , eExtraHeavyGloss (44) , eHPIJTrans (45) , eHPSnowman160 (46) , eHPSnowman220 (47) , eHPPremMatte (48) , eHPBrochMatte (49) , eHPCoverMatte (50) , eHPMatte (51) , eCoverMatte (52) , eHPOfficePaper (53) , eHPOfficePaperEU (54) , eLastMedia (55) }
   ACCESS      read-only
   STATUS      optional
   DESCRIPTION "Contains the media type of the printed job. The media type ofthe first page will decide the media type of the entire job.The return value of this object will only be valid when theprinter finishes printing the entire job. "
   USE ""
   INTERACTION " None. "
   OPERATION " Not destructive."
::= { job-info-accounting 2 }

-- 1.3.6.1.4.1.11.2.3.9.4.2.1.1.6.5.28.3
job-info-accounting-finishing-options  OBJECT-TYPE
   SYNTAX      enumerated { eNoFinish (1) , eOffset (2) , ePunch (3) , eStapler (4) , eFinisher (5) , eBinding (6) , eCustom1 (11) , eCustom2 (12) , eCustom3 (13) , eCustom4 (14) , eCustom5 (15) , eOther (20) }
   ACCESS      read-only
   STATUS      optional
   DESCRIPTION "Contains the finishing option used on the printed job. Thefinishing option specified for the first page will decide thefinishing option of the entire job. The return value of thisobject will only be valid when the printer finishes printingthe entire job. "
   USE ""
   INTERACTION " None. "
   OPERATION " Not destructive."
::= { job-info-accounting 3 }

-- 1.3.6.1.4.1.11.2.3.9.4.2.1.1.6.5.28.33
job-info-accounting-fixer-dots  OBJECT-TYPE
   SYNTAX      integer
   ACCESS      read-only
   STATUS      optional
   DESCRIPTION "Contains the total number of fixer pixels used in a particularjob. "
   USE ""
   INTERACTION " None. "
   OPERATION " Not destructive."
::= { job-info-accounting 33 }

-- 1.3.6.1.4.1.11.2.3.9.4.2.1.1.6.5.28.4
job-info-accounting-media-simplex-count  OBJECT-TYPE
   SYNTAX      integer
   ACCESS      read-only
   STATUS      optional
   DESCRIPTION "Contains the total number of simplex pages printed in aparticular job. "
   USE ""
   INTERACTION " None. "
   OPERATION " Not destructive."
::= { job-info-accounting 4 }

-- 1.3.6.1.4.1.11.2.3.9.4.2.1.1.6.5.28.5
job-info-accounting-media-duplex-count  OBJECT-TYPE
   SYNTAX      integer
   ACCESS      read-only
   STATUS      optional
   DESCRIPTION "Contains the total number of duplex pages printed in aparticular job. "
   USE ""
   INTERACTION " None. "
   OPERATION " Not destructive."
::= { job-info-accounting 5 }

-- 1.3.6.1.4.1.11.2.3.9.4.2.1.1.6.5.28.6
job-info-accounting-grayscale-impression-count  OBJECT-TYPE
   SYNTAX      integer
   ACCESS      read-only
   STATUS      optional
   DESCRIPTION "Contains the total number of monochrome pages printed in aparticular job. "
   USE ""
   INTERACTION " None. "
   OPERATION " Not destructive."
::= { job-info-accounting 6 }

-- 1.3.6.1.4.1.11.2.3.9.4.2.1.1.6.5.28.7
job-info-accounting-color-impression-count  OBJECT-TYPE
   SYNTAX      integer
   ACCESS      read-only
   STATUS      optional
   DESCRIPTION "Contains the total number of color pages printed in aparticular job. "
   USE ""
   INTERACTION " None. "
   OPERATION " Not destructive."
::= { job-info-accounting 7 }

-- 1.3.6.1.4.1.11.2.3.9.4.2.1.1.6.5.28.8
job-info-accounting-black-dots  OBJECT-TYPE
   SYNTAX      integer
   ACCESS      read-only
   STATUS      optional
   DESCRIPTION "Contains the total number of black pixels used in a particularjob. "
   USE ""
   INTERACTION " None. "
   OPERATION " Not destructive."
::= { job-info-accounting 8 }

-- 1.3.6.1.4.1.11.2.3.9.4.2.1.1.6.5.28.9
job-info-accounting-yellow-dots  OBJECT-TYPE
   SYNTAX      integer
   ACCESS      read-only
   STATUS      optional
   DESCRIPTION "Contains the total number of yellow pixels used in a particularjob. "
   USE ""
   INTERACTION " None. "
   OPERATION " Not destructive."
::= { job-info-accounting 9 }

-- 1.3.6.1.4.1.11.2.3.9.4.2.1.1.6.7.1.1
held-job-user-name  OBJECT-TYPE
   SYNTAX      string
   ACCESS      read-only
   STATUS      optional
   DESCRIPTION "User name that is obtained by the driver through some internalmethod or from user input. "
   USE ""
   INTERACTION " None. "
   OPERATION " Not destructive."
::= { held-job-info 1 }

-- 1.3.6.1.4.1.11.2.3.9.4.2.1.1.6.7.1.2
held-job-job-name  OBJECT-TYPE
   SYNTAX      string
   ACCESS      read-only
   STATUS      optional
   DESCRIPTION "The job name may be generated by the driver or obtained fromuser input. "
   USE ""
   INTERACTION " None. "
   OPERATION " Not destructive."
::= { held-job-info 2 }

-- 1.3.6.1.4.1.11.2.3.9.4.2.1.1.6.7.1.3
held-job-retention  OBJECT-TYPE
   SYNTAX      enumerated { eHoldOff (1) , eHoldOn (2) , eHoldStore (3) , eHoldProof (4) }
   ACCESS      read-only
   STATUS      optional
   DESCRIPTION "Indicates the retention classification of the job. The valuesindicate whether the job is printed immediately or stored.There are 4 options: \\eHoldOff: The job is printed but not retained on the disk.\\eHoldOn: The job is printed and stored temporarily on thedisk. \\eHoldStore: The job is not printed but stored on the disk.\\eHoldProof: One copy of the job is printed and theremaining copies are stored on the disk. \\ "
   USE ""
   INTERACTION "  "
   OPERATION " Not destructive."
::= { held-job-info 3 }

-- 1.3.6.1.4.1.11.2.3.9.4.2.1.1.6.7.1.4
held-job-security  OBJECT-TYPE
   SYNTAX      enumerated { eHoldTypePublic (1) , eHoldTypePrivate (2) }
   ACCESS      read-only
   STATUS      optional
   DESCRIPTION "The variable specifies the security level of the job. \\eHoldTypePublic: The job does not require a PIN in order torelease the job for printing. \\eHoldTypePrivate: The job requires a PIN in order to bereleased for printing. \\ "
   USE ""
   INTERACTION "  "
   OPERATION " Not destructive."
::= { held-job-info 4 }

-- 1.3.6.1.4.1.11.2.3.9.4.2.1.1.6.7.1.5
held-job-quantity  OBJECT-TYPE
   SYNTAX      integer
   ACCESS      read-only
   STATUS      optional
   DESCRIPTION "Number of copies to print. "
   USE ""
   INTERACTION "  "
   OPERATION " Not destructive."
::= { held-job-info 5 }

-- 1.3.6.1.4.1.11.2.3.9.4.2.1.1.6.7.1.6
held-job-pin  OBJECT-TYPE
   SYNTAX      string
   ACCESS      read-only
   STATUS      optional
   DESCRIPTION "A string that is specified in the job stream and then requiredto be entered in order to release the job for printing. PINstands for Personal Identification Number. "
   USE ""
   INTERACTION "  "
   OPERATION " Not destructive."
::= { held-job-info 6 }

-- 1.3.6.1.4.1.11.2.3.9.4.2.1.1.6.7.2.1
held-job-print  OBJECT-TYPE
   SYNTAX      binary
   ACCESS      write-only
   STATUS      optional
   DESCRIPTION "Instructs the printer to schedule the specified held job forprinting with the specified number of copies. The job-id isused to identify which job to print. A held job can also beprinted from the control panel. "
   USE ""
   INTERACTION "  "
   OPERATION " "
::= { held-job-control 1 }

-- 1.3.6.1.4.1.11.2.3.9.4.2.1.1.6.7.2.2
held-job-delete  OBJECT-TYPE
   SYNTAX      integer
   ACCESS      write-only
   STATUS      optional
   DESCRIPTION "Instructs the printer to delete the specified held job from thelist. The job-id is used to identify which job to delete. Aheld job can also be deleted from the control panel. "
   USE ""
   INTERACTION "  "
   OPERATION " "
::= { held-job-control 2 }

-- 1.3.6.1.4.1.11.2.3.9.4.2.1.1.6.7.2.3
held-job-set-queue-size  OBJECT-TYPE
   SYNTAX      integer
   ACCESS      read-write
   STATUS      optional
   DESCRIPTION "Sets the maximum number of jobs which can be stored in the heldjob list. "
   USE ""
   INTERACTION "  "
   OPERATION " "
::= { held-job-control 3 }

-- 1.3.6.1.4.1.11.2.3.9.4.2.1.1.6.7.2.4
held-job-enable  OBJECT-TYPE
   SYNTAX      enumerated { eDisabled (1) , eEnabled (2) }
   ACCESS      read-write
   STATUS      optional
   DESCRIPTION "Enables or disables Job Retention (Job Hold). The valid valuesare eDisabled and eEnabled. (Specifying an invalid mode causesan &lt;ErrorInvalidOrUnsupportedValue&gt; error to be returned.) WheneDisabled is specified all Job Retention (Hold, Proof, Store,PIN Printing) is disabled. When eEnabled is specified, the JobRetention characteristics of a given job are defined by the PJLvariable SET HOLD. "
   USE ""
   INTERACTION "  "
   OPERATION " Not destructive."
::= { held-job-control 4 }

-- 1.3.6.1.4.1.11.2.3.9.4.2.1.2.1.1.1
io-timeout  OBJECT-TYPE
   SYNTAX      integer
   ACCESS      read-write
   STATUS      optional
   DESCRIPTION "The amount of time, in seconds, to wait for more print job datato be received before an I/O timeout occurs. The I/O channelbeing timed is the I/O channel that received the dataassociated with the current print job. If an I/O timeoutoccurs, the PDL processing sub-system assumes all the dataassociated with the current print job has been received, andprocesses the end of job in a PDL specific manner. The POSspecifies the supported values. "
   USE ""
   INTERACTION " May not be settable if NOT-IDLE contains the cProcessingPDLitem. "
   OPERATION " Not destructive."
::= { settings-io 1 }

-- 1.3.6.1.4.1.11.2.3.9.4.2.1.2.1.1.2
io-switch  OBJECT-TYPE
   SYNTAX      enumerated { eYes (1) }
   ACCESS      read-only
   STATUS      optional
   DESCRIPTION "Indicates if the device will switch between I/O channels when ajob boundary is encountered and print job data is available onanother I/O channel. "
   USE ""
   INTERACTION " None. "
   OPERATION " Not destructive."
::= { settings-io 2 }

-- 1.3.6.1.4.1.11.2.3.9.4.2.1.2.2.1.63
scanner-accessory-total-copy-pages-printed  OBJECT-TYPE
   SYNTAX      integer
   ACCESS      read-only
   STATUS      optional
   DESCRIPTION "This relates to the number of copy pages printed on a device.The output sheet that is duplexed (made 2- sided) should becounted as 2 pages. "
   USE ""
   INTERACTION "  "
   OPERATION " Not destructive."
::= { settings-scanner 63 }

-- 1.3.6.1.4.1.11.2.3.9.4.2.1.3.3.1.11
default-lines-per-page  OBJECT-TYPE
   SYNTAX      integer
   ACCESS      read-write
   STATUS      optional
   DESCRIPTION "Returns or changes the default number of lines per page. ThePOS indicates the supported values. An unsupported value causesthe printer to use the closest supported value, causing theprinter to return the &lt;OKNearestLegalValueSubstituted&gt;. "
   USE ""
   INTERACTION " Future devices are encouraged to support the DEFAULT-VMI objectas this object will eventually be obsoleted. May not besettable if NOT-IDLE contains the cProcessingPDL item. "
   OPERATION " Not destructive."
::= { settings-pdl 11 }

-- 1.3.6.1.4.1.11.2.3.9.4.2.1.3.3.1.12
default-vmi  OBJECT-TYPE
   SYNTAX      integer
   ACCESS      read-write
   STATUS      optional
   DESCRIPTION "Returns or changes the default vertical motion index. The unitof measure for VMI is centipoints per line. The POS indicatesthe supported values. An unsupported value causes the printerto use the closest supported value, causing the printer toreturn &lt;OKNearestLegalValueSubstituted&gt;. "
   USE ""
   INTERACTION " May not be settable if NOT-IDLE contains the cProcessingPDLitem. "
   OPERATION " Not destructive."
::= { settings-pdl 12 }

-- 1.3.6.1.4.1.11.2.3.9.4.2.1.3.3.1.13
default-media-size  OBJECT-TYPE
   SYNTAX      enumerated { eUSExecutive (1) , eUSLetter (2) , eUSLegal (3) , eUSEDP (4) , eEuropeanEDP (5) , eReservedDoNotUse (6) , eUSGovernmentLetter (7) , eUSGovernmentLegal (8) , eFolio (9) , eFoolscap (10) , eLedger (11) , eCSize (12) , eDSize (13) , eESize (14) , eStatement (15) , eSuperB (16) , eROC16K (17) , eJISExecutive (18) , eROC8K (19) , eISOandJISA10 (20) , eISOandJISA9 (21) , eISOandJISA8 (22) , eISOandJISA7 (23) , eISOandJISA6 (24) , eISOandJISA5 (25) , eISOandJISA4 (26) , eISOandJISA3 (27) , eISOandJISA2 (28) , eISOandJISA1 (29) , eISOandJISA0 (30) , eISOandJIS2A0 (31) , eISOandJIS4A0 (32) , ePRC8K270X390 (33) , ePRC16K195X270 (34) , ePRC8K260X368 (35) , eISORA4 (36) , eISOSRA4 (37) , eISORA3 (39) , eJISB10 (40) , eJISB9 (41) , eJISB8 (42) , eJISB7 (43) , eJISB6 (44) , eJISB5 (45) , eJISB4 (46) , eJISB3 (47) , eJISB2 (48) , eJISB1 (49) , eJISB0 (50) , eISOB10 (60) , eISOB9 (61) , eISOB8 (62) , eISOB7 (63) , eISOB6 (64) , eISOB5 (65) , eISOB4 (66) , eISOB3 (67) , eISOB2 (68) , eISOB1 (69) , eISOB0 (70) , eJapansePostcardSingle (71) , eJapansePostcardDouble (72) , eISOA6Postcard (73) , eIndexCard4x6 (74) , eIndexCard5x8 (75) , ePhoto4x6 (76) , eJapanesePostcardWithTab (77) , eIndexCard3x5 (78) , eCommercial9 (79) , eMonarch (80) , eCommercial10 (81) , eCatalog (82) , eNo10Envelope (83) , ePRC16K184X260 (89) , eInternationalDL (90) , eInternationalC5 (91) , eInternationalC6 (92) , eInternationalC4 (93) , eInternationalB5 (100) , eCustom (101) , eCustomCard (108) , eUSEnvelopeA2 (109) , eJapanseEnvLong3 (110) , eJapanseEnvLong4 (111) , eJapaneseEnv2 (112) , ePhoto10x15 (118) , ePhotoCabinet (119) , eTabloidExtra (120) , ePhotoLSizeCard (121) , eIndexCard5x7 (122) , ePhotoESizeCard (123) , ePhotoKGSizeCard (124) , ePhoto2ESizeCard (125) , ePhoto2LSizeCard (126) , eUSExecutiveR (257) , eUSLetterR (258) , eROC16KR (273) , eISOandJISA6R (280) , eISOandJISA5R (281) , eISOandJISA4R (282) , eJISBR6R (300) , eJISB5R (301) , eStatementR (302) , eAnyCustomSize (32764) , eAnySize (32765) , eCustomRoll (32766) , eUnknownMediaSize (32767) , eStatementWR (65234) , eJISB5WR (65235) , eISOandJISA4WR (65254) , eISOandJISA5WR (65255) , eUSLetterWR (65278) , eJISB4W (65490) , eJISB5W (65491) , eISOandJISA3W (65509) , eISOandJISA4W (65510) , eISOandJISA5W (65511) , eStatementW (65521) , eLedgerW (65530) , eUSLetterW (65534) }
   ACCESS      read-write , trappable
   STATUS      optional
   DESCRIPTION "This indicates the default media size. A write of anunsupported value causes an &lt;ErrorInvalidOrUnsupported Value&gt;.Complete list of supported media sizes along with theirdimensions are listed in the ''Media Size Table'' near the endof this document. (for a full list of media size enums see theend of this file)  "
   USE ""
   INTERACTION " May not be settable if NOT-IDLE contains the cProcessingPDLitem. "
   OPERATION " Not destructive."
::= { settings-pdl 13 }

-- 1.3.6.1.4.1.11.2.3.9.4.2.1.3.3.1.19
cold-reset-media-size  OBJECT-TYPE
   SYNTAX      enumerated { eUSExecutive (1) , eUSLetter (2) , eUSLegal (3) , eUSEDP (4) , eEuropeanEDP (5) , eReservedDoNotUse (6) , eUSGovernmentLetter (7) , eUSGovernmentLegal (8) , eFolio (9) , eFoolscap (10) , eLedger (11) , eCSize (12) , eDSize (13) , eESize (14) , eStatement (15) , eSuperB (16) , eROC16K (17) , eJISExecutive (18) , eROC8K (19) , eISOandJISA10 (20) , eISOandJISA9 (21) , eISOandJISA8 (22) , eISOandJISA7 (23) , eISOandJISA6 (24) , eISOandJISA5 (25) , eISOandJISA4 (26) , eISOandJISA3 (27) , eISOandJISA2 (28) , eISOandJISA1 (29) , eISOandJISA0 (30) , eISOandJIS2A0 (31) , eISOandJIS4A0 (32) , ePRC8K270X390 (33) , ePRC16K195X270 (34) , ePRC8K260X368 (35) , eJISB10 (40) , eJISB9 (41) , eJISB8 (42) , eJISB7 (43) , eJISB6 (44) , eJISB5 (45) , eJISB4 (46) , eJISB3 (47) , eJISB2 (48) , eJISB1 (49) , eJISB0 (50) , eISOB10 (60) , eISOB9 (61) , eISOB8 (62) , eISOB7 (63) , eISOB6 (64) , eISOB5 (65) , eISOB4 (66) , eISOB3 (67) , eISOB2 (68) , eISOB1 (69) , eISOB0 (70) , eJapansePostcardSingle (71) , eJapansePostcardDouble (72) , eISOA6Postcard (73) , eIndexCard4x6 (74) , eIndexCard5x8 (75) , ePhoto4x6 (76) , eJapanesePostcardWithTab (77) , eIndexCard3x5 (78) , eMonarch (80) , eCommercial10 (81) , eCatalog (82) , eNo10Envelope (83) , ePRC16K184X260 (89) , eInternationalDL (90) , eInternationalC5 (91) , eInternationalC6 (92) , eInternationalC4 (93) , eInternationalB5 (100) , eCustom (101) , eCustomCard (108) , eUSEnvelopeA2 (109) , eJapanseEnvLong3 (110) , eJapanseEnvLong4 (111) , eJapaneseEnv2 (112) , ePhoto10x15 (118) , ePhotoCabinet (119) , ePhotoLSizeCard (121) , eIndexCard5x7 (122) , ePhotoESizeCard (123) , ePhotoKGSizeCard (124) , ePhoto2ESizeCard (125) , ePhoto2LSizeCard (126) , eUSExecutiveR (257) , eUSLetterR (258) , eROC16KR (273) , eISOandJISA6R (280) , eISOandJISA5R (281) , eISOandJISA4R (282) , eJISBR6R (300) , eJISB5R (301) , eStatementR (302) , eAnyCustomSize (32764) , eAnySize (32765) , eCustomRoll (32766) , eUnknownMediaSize (32767) , eStatementWR (65234) , eJISB5WR (65235) , eISOandJISA4WR (65254) , eISOandJISA5WR (65255) , eUSLetterWR (65278) , eJISB4W (65490) , eJISB5W (65491) , eISOandJISA3W (65509) , eISOandJISA4W (65510) , eISOandJISA5W (65511) , eStatementW (65521) , eLedgerW (65530) , eUSLetterW (65534) }
   ACCESS      read-write
   STATUS      optional
   DESCRIPTION "Returns or sets the media size that is used as theDEFAULT-MEDIA-SIZE when a cold reset occurs. "
   USE ""
   INTERACTION " May not be settable if NOT-IDLE contains the cProcessingPDLitem. If successfully set, effects the value DEFAULT-MEDIA-SIZEis set to after a cold reset. "
   OPERATION " Not destructive."
::= { settings-pdl 19 }

-- 1.3.6.1.4.1.11.2.3.9.4.2.1.3.3.1.22
default-media-name  OBJECT-TYPE
   SYNTAX      string
   ACCESS      read-write
   STATUS      optional
   DESCRIPTION "Returns or sets the media name that is used until the medianame is changed by a print job command. "
   USE ""
   INTERACTION " None. "
   OPERATION " Not destructive."
::= { settings-pdl 22 }

-- 1.3.6.1.4.1.11.2.3.9.4.2.1.3.3.1.36
reprint  OBJECT-TYPE
   SYNTAX      enumerated { eOff (1) , eOn (2) , eAuto (3) }
   ACCESS      read-write
   STATUS      optional
   DESCRIPTION "Returns or changes the reprint (jam recovery) setting. If eOn,then the device will reprint pages jammed pages. If eOff, thedevice will not attempt to reprint jammed pages. If eAuto, adevice dependent algorithm (which should be documented in thePOS) will be used to determine if the page gets reprinted. Thisobject controls all PDLs, unless a specific PDL supports itsown reprint control mechanism. To date, only PostScript has aPDL reprint control mechanism. "
   USE ""
   INTERACTION " The POSTSCRIPT-JAM-RECOVERY object may override this setting.The interaction of REPRINT and POSTSCRIPT-JAM-RECOVERY isdevice dependent. "
   OPERATION " Not destructive."
::= { settings-pdl 36 }

-- 1.3.6.1.4.1.11.2.3.9.4.2.1.3.3.1.39
default-bits-per-pixel  OBJECT-TYPE
   SYNTAX      integer
   ACCESS      read-write
   STATUS      optional
   DESCRIPTION "Controls the number of levels used (per pixel) when printinggrayscale or color images. "
   USE ""
   INTERACTION " None. "
   OPERATION " Not destructive."
::= { settings-pdl 39 }

-- 1.3.6.1.4.1.11.2.3.9.4.2.1.3.3.1.4
default-copies  OBJECT-TYPE
   SYNTAX      integer
   ACCESS      read-write
   STATUS      optional
   DESCRIPTION "Returns or changes default copies. Default copies is thedefault values used by the PDL to control the number of copiesof each page in the print job that are printed. The print jobcan override this value. The list of supported values should bedocumented in the device POS. "
   USE ""
   INTERACTION " May not be settable if NOT-IDLE contains the cProcessingPDLitem. "
   OPERATION " Not destructive."
::= { settings-pdl 4 }

-- 1.3.6.1.4.1.11.2.3.9.4.2.1.3.3.1.5
form-feed  OBJECT-TYPE
   SYNTAX      enumerated { eInitiateAction (1) }
   ACCESS      write-only
   STATUS      optional
   DESCRIPTION "Instructs the PDL processing sub-system to finishing processingthe current page of the current job. Form feed is also known asclose page or eject page. If the PDL processing sub-system isin a FORM-FEED-NEEDED state, this causes the device to flush orfinish processing the current page of the current job. If thedevice is not in the FORM-FEED-NEEDED state, an&lt;ErrorActionCanNotBePerformedNow&gt; will occur. "
   USE ""
   INTERACTION " Only writable when FORM-FEED-NEEDED is eTrue. "
   OPERATION " This action may interrupt the current job. The device mayexecute a PDL reset (which may cause device dependent actionsto occur)."
::= { settings-pdl 5 }

-- 1.3.6.1.4.1.11.2.3.9.4.2.1.3.3.1.8
default-vertical-black-resolution  OBJECT-TYPE
   SYNTAX      integer
   ACCESS      read-write
   STATUS      optional
   DESCRIPTION "Returns or changes the value of the default vertical blackresolution. The units are dots per inch. "
   USE ""
   INTERACTION " May not be settable if NOT-IDLE contains the cProcessingPDLitem. Some devices have restrictions on what vertical andhorizontal resolutions are supported. Changing theDEFAULT-VERTICAL-BLACK-RESOLUTION may cause theDEFAULT-HORIZONTAL-BLACK-RESOLUTION to also change. "
   OPERATION " Not destructive."
::= { settings-pdl 8 }

-- 1.3.6.1.4.1.11.2.3.9.4.2.1.3.3.1.9
default-horizontal-black-resolution  OBJECT-TYPE
   SYNTAX      integer
   ACCESS      read-write
   STATUS      optional
   DESCRIPTION "Returns or changes the value of the default horizontal blackresolution. The units are dots per inch. "
   USE ""
   INTERACTION " May not be settable if NOT-IDLE contains the cProcessingPDLitem. Some devices have restrictions on what vertical andhorizontal resolutions are supported. Changing theDEFAULT-HORIZONTAL-BLACK-RESOLUTION may cause theDEFAULT-VERTICAL-BLACK-RESOLUTION to also change. "
   OPERATION " Not destructive."
::= { settings-pdl 9 }

-- 1.3.6.1.4.1.11.2.3.9.4.2.1.3.3.15.1
pdf-version  OBJECT-TYPE
   SYNTAX      string
   ACCESS      read-only
   STATUS      optional
   DESCRIPTION "Contains version of PDF that is supported on the device. "
   USE ""
   INTERACTION " None. "
   OPERATION " Not destructive."
::= { pdl-pdf 1 }

-- 1.3.6.1.4.1.11.2.3.9.4.2.1.3.3.15.2
pdf-total-page-count  OBJECT-TYPE
   SYNTAX      integer
   ACCESS      read-only
   STATUS      optional
   DESCRIPTION "Total number of PDF pages printed by the device. "
   USE ""
   INTERACTION " None. "
   OPERATION " Not destructive."
::= { pdl-pdf 2 }

-- 1.3.6.1.4.1.11.2.3.9.4.2.1.3.3.15.3
pdf-enabled  OBJECT-TYPE
   SYNTAX      enumerated { ePDFNotEnabled (1) , ePDFEnabled (2) }
   ACCESS      read-only
   STATUS      optional
   DESCRIPTION "Used to tell whether the device supports PDF. "
   USE ""
   INTERACTION " None. "
   OPERATION " Not destructive."
::= { pdl-pdf 3 }

-- 1.3.6.1.4.1.11.2.3.9.4.2.1.3.3.15.4
pdf-print-errors  OBJECT-TYPE
   SYNTAX      enumerated { eOff (1) , eOn (2) }
   ACCESS      read-write
   STATUS      optional
   DESCRIPTION "Returns or changes the value of the print PDF errors setting.If eOn, PDF prints an error page showing the error encounteredand the stack at the time of the error. "
   USE ""
   INTERACTION " May not be settable if NOT-IDLE contains the cProcessingPDLitem. "
   OPERATION " Not destructive."
::= { pdl-pdf 4 }

-- 1.3.6.1.4.1.11.2.3.9.4.2.1.3.3.2.2
form-feed-needed  OBJECT-TYPE
   SYNTAX      enumerated { eFalse (1) , eTrue (2) }
   ACCESS      read-only , trappable
   STATUS      optional
   DESCRIPTION "Indicates if the PDL processing sub-system has made marks onthe current page and the source subsystem has been idle for adevice specific amount of time. "
   USE ""
   INTERACTION " None. "
   OPERATION " Not destructive."
::= { status-pdl 2 }

-- 1.3.6.1.4.1.11.2.3.9.4.2.1.3.3.3.14
pcl-default-font-source  OBJECT-TYPE
   SYNTAX      enumerated { eInternal (1) , ePermanentSoft (2) , eRomSimm1 (10) , eRomSimm2 (11) , eRomSimm3 (12) , eRomSimm4 (13) , eRomSimm5 (14) , eUsb1 (15) , eUsb2 (16) , eUsb3 (17) , eUsb4 (18) }
   ACCESS      read-write
   STATUS      optional
   DESCRIPTION "Returns or changes the value of the default font sourcevariable in NVRAM. "
   USE ""
   INTERACTION " May not be settable if NOT-IDLE contains the cProcessingPDLitem. "
   OPERATION " Not destructive."
::= { pdl-pcl 14 }

-- 1.3.6.1.4.1.11.2.3.9.4.2.1.3.3.3.15
pcl-default-font-number  OBJECT-TYPE
   SYNTAX      integer
   ACCESS      read-write
   STATUS      optional
   DESCRIPTION "Returns or changes the value of the default font numbervariable in NVRAM. Writing an unsupported value causes theprinter to generate an &lt;ErrorInvalidOrUnsupportedValue&gt;. "
   USE ""
   INTERACTION " May not be settable if NOT-IDLE contains the cProcessingPDLitem. "
   OPERATION " Not destructive."
::= { pdl-pcl 15 }

-- 1.3.6.1.4.1.11.2.3.9.4.2.1.3.3.3.5
pcl-total-page-count  OBJECT-TYPE
   SYNTAX      integer
   ACCESS      read-only
   STATUS      optional
   DESCRIPTION "Total number of PCL pages printed by the device. "
   USE ""
   INTERACTION " None. "
   OPERATION " Not destructive."
::= { pdl-pcl 5 }

-- 1.3.6.1.4.1.11.2.3.9.4.2.1.3.3.4.11
postscript-print-errors  OBJECT-TYPE
   SYNTAX      enumerated { eOff (1) , eOn (2) }
   ACCESS      read-write
   STATUS      optional
   DESCRIPTION "Returns or changes the value of the print PostScript errorssetting. If eOn, PostScript prints an error page showing theerror encountered and the stack at the time of the error. "
   USE ""
   INTERACTION " May not be settable if NOT-IDLE contains the cProcessingPDLitem. "
   OPERATION " Not destructive."
::= { pdl-postscript 11 }

-- 1.3.6.1.4.1.11.2.3.9.4.2.1.3.3.4.14
postscript-defer-media  OBJECT-TYPE
   SYNTAX      enumerated { eDisabled (1) , eEnabled (2) }
   ACCESS      read-write
   STATUS      optional
   DESCRIPTION "This object will be used to enable or disable the use of theAdobe Postscript Paper Handling Model in the printer firmware.By default it is enabled which means that PostScript willalways defer the media selection to HP Paper Handling Model. "
   USE ""
   INTERACTION " None. "
   OPERATION " Not destructive."
::= { pdl-postscript 14 }

-- 1.3.6.1.4.1.11.2.3.9.4.2.1.3.3.4.5
postscript-total-page-count  OBJECT-TYPE
   SYNTAX      integer
   ACCESS      read-only
   STATUS      optional
   DESCRIPTION "Total number of PostScript pages printed by the device. "
   USE ""
   INTERACTION " None. "
   OPERATION " Not destructive."
::= { pdl-postscript 5 }

-- 1.3.6.1.4.1.11.2.3.9.4.2.1.4.1.1.2
override-media-name  OBJECT-TYPE
   SYNTAX      string
   ACCESS      read-write
   STATUS      optional
   DESCRIPTION "Sets a string identifying the media name that is to be used inplace of the currently requested media. The substitution willcontinue until another media is selected. If set to a namedmedia that is not currently available the requested media isnot overridden. "
   USE ""
   INTERACTION " None. "
   OPERATION " Not destructive."
::= { settings-prt-eng 2 }

-- 1.3.6.1.4.1.11.2.3.9.4.2.1.4.1.1.28
duplex-blank-pages  OBJECT-TYPE
   SYNTAX      enumerated { eDuplexBlankPagesAuto (1) , eDuplexBlankPagesYes (2) }
   ACCESS      read-write
   STATUS      optional
   DESCRIPTION "When the value of the device-system variable is set toeDuplexBlankPagesAuto, it means to Smart Duplex in any of thespecified conditions. This selection is logically equivalent to'NO, do not duplex blank pages if not duplexing them obtains aperformance enhancement'. When the value of the device-system variableis set to eDuplexBlankPagesYes, it means to disable SmartDuplexing. "
   USE ""
   INTERACTION " The value of this object can be changed via the Control Panelmenu and through PML. "
   OPERATION " Not destructive."
::= { settings-prt-eng 28 }

-- 1.3.6.1.4.1.11.2.3.9.4.2.1.4.1.1.3
override-media-size  OBJECT-TYPE
   SYNTAX      enumerated { eUSExecutive (1) , eUSLetter (2) , eUSLegal (3) , eUSEDP (4) , eEuropeanEDP (5) , eReservedDoNotUse (6) , eUSGovernmentLetter (7) , eUSGovernmentLegal (8) , eFolio (9) , eFoolscap (10) , eLedger (11) , eCSize (12) , eDSize (13) , eESize (14) , eStatement (15) , eSuperB (16) , eROC16K (17) , eJISExecutive (18) , eROC8K (19) , eISOandJISA10 (20) , eISOandJISA9 (21) , eISOandJISA8 (22) , eISOandJISA7 (23) , eISOandJISA6 (24) , eISOandJISA5 (25) , eISOandJISA4 (26) , eISOandJISA3 (27) , eISOandJISA2 (28) , eISOandJISA1 (29) , eISOandJISA0 (30) , eISOandJIS2A0 (31) , eISOandJIS4A0 (32) , ePRC8K270X390 (33) , ePRC16K195X270 (34) , ePRC8K260X368 (35) , eJISB10 (40) , eJISB9 (41) , eJISB8 (42) , eJISB7 (43) , eJISB6 (44) , eJISB5 (45) , eJISB4 (46) , eJISB3 (47) , eJISB2 (48) , eJISB1 (49) , eJISB0 (50) , eISOB10 (60) , eISOB9 (61) , eISOB8 (62) , eISOB7 (63) , eISOB6 (64) , eISOB5 (65) , eISOB4 (66) , eISOB3 (67) , eISOB2 (68) , eISOB1 (69) , eISOB0 (70) , eJapansePostcardSingle (71) , eJapansePostcardDouble (72) , eISOA6Postcard (73) , eIndexCard4x6 (74) , eIndexCard5x8 (75) , ePhoto4x6 (76) , eJapanesePostcardWithTab (77) , eIndexCard3x5 (78) , eMonarch (80) , eCommercial10 (81) , eCatalog (82) , eNo10Envelope (83) , ePRC16K184X260 (89) , eInternationalDL (90) , eInternationalC5 (91) , eInternationalC6 (92) , eInternationalC4 (93) , eInternationalB5 (100) , eCustom (101) , eEnvelope9 (102) , eCustomCard (108) , eUSEnvelopeA2 (109) , eJapanseEnvLong3 (110) , eJapanseEnvLong4 (111) , eJapaneseEnv2 (112) , ePhoto10x15 (118) , ePhotoCabinet (119) , ePhotoLSizeCard (121) , eIndexCard5x7 (122) , ePhotoESizeCard (123) , ePhotoKGSizeCard (124) , ePhoto2ESizeCard (125) , ePhoto2LSizeCard (126) , eUSExecutiveR (257) , eUSLetterR (258) , eROC16KR (273) , eISOandJISA6R (280) , eISOandJISA5R (281) , eISOandJISA4R (282) , eJISBR6R (300) , eJISB5R (301) , eStatementR (302) , eAnyCustomSize (32764) , eAnySize (32765) , eCustomRoll (32766) , eUnknownMediaSize (32767) , eStatementWR (65234) , eJISB5WR (65235) , eISOandJISA4WR (65254) , eISOandJISA5WR (65255) , eUSLetterWR (65278) , eJISB4W (65490) , eJISB5W (65491) , eISOandJISA3W (65509) , eISOandJISA4W (65510) , eISOandJISA5W (65511) , eStatementW (65521) , eLedgerW (65530) , eUSLetterW (65534) }
   ACCESS      read-write
   STATUS      optional
   DESCRIPTION "Sets the media size that is to be used in place of thecurrently requested media size. "
   USE ""
   INTERACTION " None. "
   OPERATION " Not destructive."
::= { settings-prt-eng 3 }

-- 1.3.6.1.4.1.11.2.3.9.4.2.1.4.1.1.31
finisher-image-rotation  OBJECT-TYPE
   SYNTAX      binary
   ACCESS      read-write
   STATUS      optional
   DESCRIPTION "This PML object will provide the additional image rotation thatis applied to a printed job depending on the presence orabsence of a finisher device or the value of theSVM_ALWAYS_MATCH_OUTPUT_ORIENTATION variable. "
   USE ""
   INTERACTION " Through PML set and get commands "
   OPERATION " Not destructive."
::= { settings-prt-eng 31 }

-- 1.3.6.1.4.1.11.2.3.9.4.2.1.4.1.1.36
cartridge-adaptive-gain  OBJECT-TYPE
   SYNTAX      real
   ACCESS      read-only
   STATUS      optional
   DESCRIPTION "The Adaptive TA Gain is stored for the last 5 cartridges.Cartridge one is the most recent to be installed (current), andcartridge 5 is least recent to be installed. This object isdouble array object. OID extension isCARTRIDGE-ADAPTIVE-GAIN.x.n, where x is 1..4 (x is Black, Cyan,Magenta, Yellow Toner), and n is 1..5 (n is number ofcartridges). "
   USE ""
   INTERACTION " None. "
   OPERATION " Not destructive."
::= { settings-prt-eng 36 }

-- 1.3.6.1.4.1.11.2.3.9.4.2.1.4.1.1.37
cartridge-adaptive-gain-reset  OBJECT-TYPE
   SYNTAX      enumerated { eFalse (1) , eTrue (2) }
   ACCESS      write-only
   STATUS      optional
   DESCRIPTION "This object will Reset the Adaptive TA Gain value to 1.00 anddisable the adaptive TA routine. The value that this objectreturns is stored in non-volatile memory. "
   USE ""
   INTERACTION " None "
   OPERATION " Not destructive."
::= { settings-prt-eng 37 }

-- 1.3.6.1.4.1.11.2.3.9.4.2.1.4.1.1.38
supplies-at-very-low-setting  OBJECT-TYPE
   SYNTAX      enumerated { eStopAtOut (2) , eOverrideAtOut (4) , ePromptAtOut (6) , ePrintBlack (7) }
   ACCESS      read-write
   STATUS      optional
   DESCRIPTION "This object can be used to change the setting of menu item ATVERY LOW. The behavior of the printer when a supply reaches lowchanges in accordance with the setting of this PML Object. Ifthe option eStopAtOut is selected then printer will stop when asupply reaches Estimated End of Life (EEOL). If the optioneOverrideAtOut is selected then printer will continue past EEOLin override mode. If the option eOverrideAtOut is selected thenprinter will continue past EEOL in override mode. If the optionePromptAtOut is selected then printer will ask the user if theywish to continue printing past EEOL in override mode. If theoption eAutoContinueBlack is selected then printer willcontinue printing in mono past EEOL. This may be subject topage limits. (Color only) NOTE: This object replacesSUPPLIES-REPLACE-ACTION-AT-SETTING "
   USE ""
   INTERACTION " On NVRAM init the object will be set to default value which istypically eOverrideAtOut for mono and ePromptAtOut for colorproducts. "
   OPERATION " Not destructive."
::= { settings-prt-eng 38}

-- 1.3.6.1.4.1.11.2.3.9.4.2.1.4.1.1.5
print-density  OBJECT-TYPE
   SYNTAX      integer (0..10)
   ACCESS      read-write
   STATUS      optional
   DESCRIPTION "Returns or sets the print density setting. Print density is theinstantaneous amount of marking agent applied to the paperwhile printing. A value of zero has the lowest print density,yielding a lighter page. A value of 10 has the highest printdensity, yielding a darker page. Each POS should document whatvalues in the 0 to 10 range are supported. "
   USE ""
   INTERACTION " None. "
   OPERATION " Not destructive."
::= { settings-prt-eng 5 }

-- 1.3.6.1.4.1.11.2.3.9.4.2.1.4.1.10.11
consumable-pages-printed-with-supply  OBJECT-TYPE
   SYNTAX      integer
   ACCESS      read-only
   STATUS      optional
   DESCRIPTION "This PML object returns the number of pages printed with acartridge consumable. This PML object returns the value thatshould be displayed under 'Pages Printed With This Supply' forcartridges in color products. "
   USE ""
   INTERACTION " None. "
   OPERATION " Not destructive."
::= { consumables 11 }

-- 1.3.6.1.4.1.11.2.3.9.4.2.1.4.1.10.15
total-kilo-pixels-per-cartridge  OBJECT-TYPE
   SYNTAX      integer
   ACCESS      read-only
   STATUS      optional
   DESCRIPTION "Returns the total number of kilo-pixels at 600dpi in thecartridge. That is, the number returned by this object shouldbe multiplied by 1000 to determine the total number of pixelsat 600dpi in the cartridge. "
   USE ""
   INTERACTION " None. "
   OPERATION " Not destructive."
::= { consumables 15 }

-- 1.3.6.1.4.1.11.2.3.9.4.2.1.4.1.10.2
consumable-reorder-url  OBJECT-TYPE
   SYNTAX      string
   ACCESS      read-write
   STATUS      optional
   DESCRIPTION "This object is used to read and write the URL that can be usedto reorder consumables for this device. This URL is set at thefactory but can be updated by a reseller or third party. "
   USE ""
   INTERACTION " None. "
   OPERATION " Not destructive."
::= { consumables 2 }

-- 1.3.6.1.4.1.11.2.3.9.4.2.1.4.1.10.5.1.1
consumable-life-usage-units-remaining  OBJECT-TYPE
   SYNTAX      integer
   ACCESS      read-only
   STATUS      optional
   DESCRIPTION "This object reports the current estimate of the number of usageunits that remain before this supply is depleted. An installedsupply that cannot report such a number will return a value of-2. It is the reponsibility of the host application to queryeach supply in order to determine an overall deviceUSAGE-UNITS-REMAINING number - the lowest value returned. Theunit of measure for this life estimate is determined by readingthe corresponding CONSUMABLE-LIFE-USAGE-UNITS object. "
   USE ""
   INTERACTION " None. "
   OPERATION " Not destructive."
::= { consumables-life 1 }

-- 1.3.6.1.4.1.11.2.3.9.4.2.1.4.1.10.5.1.2
consumable-life-usage-units  OBJECT-TYPE
   SYNTAX      enumerated { ePagesRemaining (1) , eEstimatedPagesRemaining (2) , eUnknownUnits (3) , ePagesSinceLow (4) , ePagesSinceOut (5) , ePagesPicked (6) , ePercentLifeRemaining (7) , e4X6ImagesPrinted (8) , eEngineDropCount (9) , eEngineWebAdvances (10) }
   ACCESS      read-only
   STATUS      optional
   DESCRIPTION "This object reports current usage units in use by thecorresponding CONSUMABLE-LIFE-USAGE-UNITS-REMAINING object. "
   USE ""
   INTERACTION " None. "
   OPERATION " Not destructive."
::= { consumables-life 2 }

-- 1.3.6.1.4.1.11.2.3.9.4.2.1.4.1.10.5.1.3
consumable-life-low-threshold  OBJECT-TYPE
   SYNTAX      integer
   ACCESS      read-write
   STATUS      optional
   DESCRIPTION "This object is used to report and modify a threshold valueindicating the point in the life of a consumable or supply atwhich a transition to a LOW state will occur. "
   USE ""
   INTERACTION " None. "
   OPERATION " Not destructive."
::= { consumables-life 3 }

-- 1.3.6.1.4.1.11.2.3.9.4.2.1.4.1.10.5.1.4
estimated-page-yield  OBJECT-TYPE
   SYNTAX      integer
   ACCESS      read-only
   STATUS      optional
   DESCRIPTION "Returns the estimated yield of the cartridge inESTIMATED-PAGE-YIELD-UNIT units. "
   USE ""
   INTERACTION " None. "
   OPERATION " Not destructive."
::= { consumables-life 4 }

-- 1.3.6.1.4.1.11.2.3.9.4.2.1.4.1.10.5.1.5
estimated-page-yield-unit  OBJECT-TYPE
   SYNTAX      enumerated { e5PercentPages (1) , eISOPages (2) }
   ACCESS      read-only
   STATUS      optional
   DESCRIPTION "Returns the unit used for ESTIMATED-PAGE-YIELD. "
   USE ""
   INTERACTION " None. "
   OPERATION " Not destructive."
::= { consumables-life 5 }

-- 1.3.6.1.4.1.11.2.3.9.4.2.1.4.1.10.7
consumable-current-state  OBJECT-TYPE
   SYNTAX      collection { cAuthLevel1 (0) , cAuthLevel2 (1) , cAuthLevel3 (2) , cAuthLevel4 (3) , cAuthLevel5 (4) , cAuthLevel6 (5) , cAuthLevel7 (6) , cGenuineHPUnsupported (8) , cELabelDefective (9) , cELabelMissing (10) , cLowCondition (11) , cOutCondition (12) , cIncorrect (13) , cMissing (14) , cPastOutCondition (15) , cConfigurableLow (16) , cExpired (17) , cFailure (18) , cLeak (19) , cUnknownManufacturer (20) , cUnsupported (21) , cUnavailable (22) , cIncompatible (23) , cStatusAreValid (31) }
   ACCESS      read-only
   STATUS      optional
   DESCRIPTION "This PML object returns the current state of the particularconsumable. \\cAuthLevel1 - Consumable is at Authentication Level 1 \\cAuthLevel2 - Consumable is at Authentication Level 2 \\cAuthLevel3 - Consumable is at Authentication Level 3 \\cAuthLevel4 - Consumable is at Authentication Level 4 \\cAuthLevel5 - Consumable is at Authentication Level 5 \\cGenuineHPUnsupported - Cartridge is GenuineHP intended foranother product \\cDefectiveMemory - Cartridge has a defective memory tag \\cMissingMemory - Memory tag is missing from the cartridge\\cLowCondition - Consumable has reached the engine lowthreshold \\cOutCondition - Consumable has reached its out threshold \\cIncorrect - Cartridge inserted is not the correct one\\cMissing - Consumable is missing from the printer \\cConfigurableLow - Consumable has reached the configurablelow threshold value \\cStatusArevalid - The status reported on other bits arevalid only if the bit is set to 1. If it is 0, thevalues are invalid. \\cExpired - Is the cartridge expired, which is determined \\by the formatter.\\cFailure - Cartridge has failed determined by the engine.\\cLeak - Cartridge has a leak as determined by the engine.\\cUnknownManufacturer - the brand of the cartridge is \\unknown as determined by the engine. \\cUnsupported --- Cartridge is not supported as determined\\by the engine. \\cIncompatible - When installed consumable is incompatible withcurrent printer. These are the possible states and whenever theconsumable is in any of these states, the appropriate bit willbe set. The cLowCondition will be set when the consumablereaches the engine low threshold, and cConfigurableLow will beset when the consumable reaches the Configurable Low thresholdvalue. For non-cartridge supplies only cLowCondition,cOutCondition, and cMissing will be supported. "
   USE ""
   INTERACTION " None. "
   OPERATION " Not destructive."
::= { consumables 7 }

-- 1.3.6.1.4.1.11.2.3.9.4.2.1.4.1.10.9
device-used-while-cartridge-out-override-active  OBJECT-TYPE
   SYNTAX      enumerated { eNotUsed (1) , eUsed (2) }
   ACCESS      read-only
   STATUS      optional
   DESCRIPTION "Returns eUsed if the device has ever been used while CartridgeOut Override is activated. Merely enabling cartridge outoverride will not cause eUsed to be returned. Cartridge OutOverride must be activated by a cartridge becoming out anddevice must be used in that mode. "
   USE ""
   INTERACTION " Power cycle or NVRAM init will have no effect on this object. "
   OPERATION " Not destructive."
::= { consumables 9 }

-- 1.3.6.1.4.1.11.2.3.9.4.2.1.4.1.15.1
media-size-supported-driver-n-string  OBJECT-TYPE
   SYNTAX      string
   ACCESS      read-only
   STATUS      mandatory
   DESCRIPTION "Returns the Driver (PJL) string used to specigy a media size,for each media size that is supported by a product. PML walk of1.4.1.15.1 will return the driver (PJL) name string for eachmedia size supported by a product. PML Get of 1.4.1.15.1.X willreturn the driver (PJL) name string of the media size whose PMLID maps to X (if it is supported). "
   USE ""
   INTERACTION " None. "
   OPERATION " NOT destructive."
::= { media-sizes 1 }

-- 1.3.6.1.4.1.11.2.3.9.4.2.1.4.1.2.22
duplex-page-count  OBJECT-TYPE
   SYNTAX      integer
   ACCESS      read-only
   STATUS      optional
   DESCRIPTION "Total number of sheets of media that have been duplex printed.A sheet is counted if it travels through the duplex page path,regardless of whether or not marks are made on the page. ThePOS will indicate if the value is kept in NVRAM. "
   USE ""
   INTERACTION " None. "
   OPERATION " Not destructive."
::= { status-prt-eng 22 }

-- 1.3.6.1.4.1.11.2.3.9.4.2.1.4.1.2.26
print-engine-revision  OBJECT-TYPE
   SYNTAX      string
   ACCESS      read-only
   STATUS      optional
   DESCRIPTION "Print engine revision string. "
   USE ""
   INTERACTION " None. "
   OPERATION " Not destructive."
::= { status-prt-eng 26 }

-- 1.3.6.1.4.1.11.2.3.9.4.2.1.4.1.2.6
total-mono-page-count  OBJECT-TYPE
   SYNTAX      integer
   ACCESS      read-only
   STATUS      optional
   DESCRIPTION "Total number of black pages printed by the device. "
   USE ""
   INTERACTION " None. "
   OPERATION " Not destructive."
::= { status-prt-eng 6 }

-- 1.3.6.1.4.1.11.2.3.9.4.2.1.4.1.2.7
total-color-page-count  OBJECT-TYPE
   SYNTAX      integer
   ACCESS      read-only
   STATUS      optional
   DESCRIPTION "Total number of color pages printed by the device. "
   USE ""
   INTERACTION " None. "
   OPERATION " Not destructive."
::= { status-prt-eng 7 }

-- 1.3.6.1.4.1.11.2.3.9.4.2.1.4.1.3.1.10
default-custom-paper-dim-unit  OBJECT-TYPE
   SYNTAX      enumerated { eTenThousandthsOfInches (3) , eMicrometers (4) }
   ACCESS      read-write
   STATUS      optional
   DESCRIPTION "The units of measure used to specify the width and height ofthe printer's default custom paper size. The unit of measure ofeTenThousandthsOfInches is 0.0001 inches. "
   USE ""
   INTERACTION " The value of this object will determine the unit of measureused for the DEFAULT-CUSTOM-PAPER-FEED-DIM and DEFAULT-CUSTOM-PAPER-XFEED-DIM objects. "
   OPERATION " Not destructive."
::= { settings-intray 10 }

-- 1.3.6.1.4.1.11.2.3.9.4.2.1.4.1.3.1.11
default-custom-paper-feed-dim  OBJECT-TYPE
   SYNTAX      integer
   ACCESS      read-write
   STATUS      optional
   DESCRIPTION "Sets the printer's default custom paper size dimension in thefeed direction (direction parallel to the direction of paperfeeding). The value for this object is specified in micrometersor tenthousandths of an inch, depending upon the value ofDEFAULT-CUSTOM-PAPER-DIM-UNIT. The valid range isengine-dependent and should be documented in the POS for eachproduct. "
   USE ""
   INTERACTION " The value for this object depends upon the unit of measurespecified by DEFAULT-CUSTOM-PAPER-DIM-UNIT. "
   OPERATION " Accessing this object identifier is NOT destructive in anymanner."
::= { settings-intray 11 }

-- 1.3.6.1.4.1.11.2.3.9.4.2.1.4.1.3.1.12
default-custom-paper-xfeed-dim  OBJECT-TYPE
   SYNTAX      integer
   ACCESS      read-write
   STATUS      optional
   DESCRIPTION "Sets the printer's default custom paper size dimension in thecross-feed direction (direction ninety degrees relative to thedirection of paper feeding). The value for this object isspecified in micrometers or tenthousandths of an inch,depending upon the value of DEFAULT-CUSTOM-PAPER-DIM-UNIT. Thevalid range is engine-dependent and should be documented in thePOS for each product. "
   USE ""
   INTERACTION " The value for this object depends upon the unit of measurespecified by DEFAULT-CUSTOM-PAPER-DIM-UNIT. "
   OPERATION " Accessing this object identifier is NOT destructive in anymanner."
::= { settings-intray 12 }

-- 1.3.6.1.4.1.11.2.3.9.4.2.1.4.1.3.1.14
input-tray-max-media-feed-dim  OBJECT-TYPE
   SYNTAX      integer
   ACCESS      read-only
   STATUS      optional
   DESCRIPTION "The maximum physical media size in the feed direction of thisinput device expressed in units of measure specified by INPUT-TRAY-MIN-MAX-DIM-UNIT. A value of (-1) implies 'unlimited', avalue of (-2) implies 'unknown'. "
   USE ""
   INTERACTION "  "
   OPERATION " Not destructive."
::= { settings-intray 14 }

-- 1.3.6.1.4.1.11.2.3.9.4.2.1.4.1.3.1.15
input-tray-max-media-xfeed-dim  OBJECT-TYPE
   SYNTAX      integer
   ACCESS      read-only
   STATUS      optional
   DESCRIPTION "The maximum physical media size across the feed direction of aparticular input device expressed in units of measure specifiedby INPUT-TRAY-MIN-MAX-DIM-UNIT. A value of (-1) implies'unlimited', a value of (-2) implies 'unknown'. "
   USE ""
   INTERACTION "  "
   OPERATION " Not destructive."
::= { settings-intray 15 }

-- 1.3.6.1.4.1.11.2.3.9.4.2.1.4.1.3.1.16
input-tray-min-media-feed-dim  OBJECT-TYPE
   SYNTAX      integer
   ACCESS      read-only
   STATUS      optional
   DESCRIPTION "The minimum physical media size in the feed direction of aparticular input device expressed in units of measure specifiedby PrtInputMinMaxDimUnit. A value of (-1) implies 'unlimited',a value of (-2) implies 'unknown'. "
   USE ""
   INTERACTION "  "
   OPERATION " Not destructive."
::= { settings-intray 16 }

-- 1.3.6.1.4.1.11.2.3.9.4.2.1.4.1.3.1.17
input-tray-min-media-xfeed-dim  OBJECT-TYPE
   SYNTAX      integer
   ACCESS      read-only
   STATUS      optional
   DESCRIPTION "The minimum physical media size across the feed direction of aparticular input device expressed in units of measure specifiedby PrtInputMinMaxDimUnit. A value of (-1) implies 'unlimited',a value of (-2) implies 'unknown'. "
   USE ""
   INTERACTION "  "
   OPERATION " Not destructive."
::= { settings-intray 17 }

-- 1.3.6.1.4.1.11.2.3.9.4.2.1.4.1.3.1.19
tray-prompt  OBJECT-TYPE
   SYNTAX      enumerated { eDoNotDisplay (1) , eDisplay (2) }
   ACCESS      read-write
   STATUS      optional
   DESCRIPTION "If this object is set to eDisplay, whenever a paper tray isopened, refilled, and closed in a printer, the end user isprompted with a message 'To change size or type press check' onthe control panel. If this object is set to eDoNotDisplay, thenthe end user will not be prompted with this message whenever apaper tray is opened, refilled, and closed in a printer. "
   USE ""
   INTERACTION "  "
   OPERATION " Not destructive."
::= { settings-intray 19 }

-- 1.3.6.1.4.1.11.2.3.9.4.2.1.4.1.3.1.2
input-tray-auto-select  OBJECT-TYPE
   SYNTAX      enumerated { eOff (1) , eOn (2) }
   ACCESS      read-write
   STATUS      optional
   DESCRIPTION "Indicates if the device will automatically try to load mediafrom the next input media tray in the auto-select sequence(defined by each device) when it cannot load media from thecurrent tray. Locked trays will not be permitted in theauto-select sequence. This object has no meaning if there isonly one unlocked input media tray. "
   USE ""
   INTERACTION "  "
   OPERATION " Not destructive."
::= { settings-intray 2 }

-- 1.3.6.1.4.1.11.2.3.9.4.2.1.4.1.4.1.4
overflow-bin  OBJECT-TYPE
   SYNTAX      integer
   ACCESS      read-write
   STATUS      optional
   DESCRIPTION "Returns or sets the bin that will be used for additional sheetsof media when the current bin is full and printing is allowedto continue. "
   USE ""
   INTERACTION " If the designated bin is deleted, this object will return toits default value. "
   OPERATION " Not destructive."
::= { settings-outbin 4 }

-- 1.3.6.1.4.1.11.2.3.9.4.2.1.4.1.6.5
default-ret  OBJECT-TYPE
   SYNTAX      enumerated { eOff (1) , eLight (2) , eMedium (3) , eDark (4) , eNotSet (5) }
   ACCESS      read-write
   STATUS      optional
   DESCRIPTION "Returns or changes the Resolution Enhancement Technologysetting. Devices that only support eOff and eOn should map allother values to eOn and always return the same non-eOff valueto indicate on. The list of supported values should bedocumented in the device POS. "
   USE ""
   INTERACTION " May not be settable if NOT-IDLE contains the cProcessingPDLitem. "
   OPERATION " Not destructive."
::= { imaging 5 }

-- 1.3.6.1.4.1.11.2.3.9.4.2.1.4.1.6.7
default-print-quality  OBJECT-TYPE
   SYNTAX      integer (0..100)
   ACCESS      read-write
   STATUS      optional
   DESCRIPTION "Returns or sets the default print quality. A value of zero hasthe lowest print quality. A value of 100 has the highest printquality. Each POS should document what values in the 0 to 100range are supported. "
   USE ""
   INTERACTION " May affect various print mode settings. "
   OPERATION " Not destructive."
::= { imaging 7 }

-- 1.3.6.1.4.1.11.2.3.9.4.2.1.4.1.7.1.1
tray-disable-use-instead  OBJECT-TYPE
   SYNTAX      enumerated { eDisabled (1) , eEnabled (2) }
   ACCESS      read-write
   STATUS      optional
   DESCRIPTION "If this object is set to eEnabled, the paper mount message thatis normally posted('To use another tray....') is turned offthereby disallowing the user to specify another tray from whichpaper can be taken for printing. However, on setting thisobject to eDisabled the paper mount message is posted allowingthe user to specify another tray for paper feed. "
   USE ""
   INTERACTION " The value of this object can be changed via the Control Panelmenu. "
   OPERATION " Not destructive."
::= { settings-ph 1 }

-- 1.3.6.1.4.1.11.2.3.9.4.2.1.4.1.7.3.2.2
phd2-device-specific-command  OBJECT-TYPE
   SYNTAX      binary
   ACCESS      write-only
   STATUS      optional
   DESCRIPTION "This object is used to send device-specific data to the paperhandling device. The meaning of the device-specific command isdependent on the paper handling device and must be specified inthe POS. If the paper handling device does not accept thecommand, then an &lt;ErrorInvalidOrUnsupportedValue&gt; will bereturned. If the device accepts the command, it may still beprocessing the command after the response has been returned.Depending on the device, the application may need to queryPHDx-DEVICE-MEMORY to see when the command has completed. "
   USE ""
   INTERACTION " Depending on the device, may interact with PHDx-DEVICE-MEMORY.The state of the device memory may be modified when the usersubmits a PHDx-DEVICE-SPECIFIC-COMMAND. "
   OPERATION " Not destructive."
::= { ph2 2 }

-- 1.3.6.1.4.1.11.2.3.9.4.2.1.4.1.8.1.1
media-names-available  OBJECT-TYPE
   SYNTAX      collection { cMediaName1Available (0) , cMediaName2Available (1) , cMediaName3Available (2) , cMediaName4Available (3) , cMediaName5Available (4) , cMediaName6Available (5) , cMediaName7Available (6) , cMediaName8Available (7) , cMediaName9Available (8) , cMediaName10Available (9) , cMediaName11Available (10) , cMediaName12Available (11) , cMediaName13Available (12) , cMediaName14Available (13) , cMediaName15Available (14) , cMediaName16Available (15) , cMediaName17Available (16) , cMediaName18Available (17) , cMediaName19Available (18) , cMediaName20Available (19) , cMediaName21Available (20) , cMediaName22Available (21) , cMediaName23Available (22) , cMediaName24Available (23) , cMediaName25Available (24) , cMediaName26Available (25) , cMediaName27Available (26) , cMediaName28Available (27) , cMediaName29Available (28) , cMediaName30Available (29) , cMediaName31Available (30) , cMediaName32Available (31) }
   ACCESS      read-write
   STATUS      optional
   DESCRIPTION "The value of this object controls which of the MEDIAx-NAMEobjects are supported. If a bit is set to zero, then attemptingto get or set the corresponding MEDIAx-NAME objects will return&lt;ErrorUnknownObjectIdentifier&gt;. "
   USE ""
   INTERACTION " MEDIAx-NAME, MEDIAx-SHORT-NAME, and MEDIAx-PAGE-COUNT objects. "
   OPERATION " Not destructive."
::= { settings-print-media 1 }

-- 1.3.6.1.4.1.11.2.3.9.4.2.1.4.1.8.1.3
media-names-enabled  OBJECT-TYPE
   SYNTAX      binary
   ACCESS      read-write
   STATUS      optional
   DESCRIPTION "The value of this object controls whish of the MEDIAx-NAMEobjects are supported. Of a bit is set to zero then the attemptto get or set the corresponding MEDIAx-NAME objects will return&lt;ErrorUnknownObjectIdentifier&gt; "
   USE ""
   INTERACTION " MEDIAx-NAME, MEDIAx-SHORT-NAME, MEDIAx-PAGE-COUNT,MEDIA-NAMES-AVAILABLE This object will enable and disable thesame bits as MEDIA-NAMES-AVAILABLE but is designed not to bebound to the 32 bit boundary. "
   OPERATION " Not destructive."
::= { settings-print-media 3 }

-- 1.3.6.1.4.1.11.2.3.9.4.2.1.4.1.8.4.1
engine-media-modes-supported1  OBJECT-TYPE
   SYNTAX      string
   ACCESS      read-only
   STATUS      optional
   DESCRIPTION "The list of engine media modes supported by the device. Themodes are each separated by a comma character. An examplestring would be: 'Normal,Rough,Low,Vellum'. "
   USE ""
   INTERACTION " The printer should localize these strings. "
   OPERATION " Not destructive."
::= { media-modes 1 }

-- 1.3.6.1.4.1.11.2.3.9.4.2.1.4.1.8.8.1
media-number-of-type-supported  OBJECT-TYPE
   SYNTAX      integer
   ACCESS      read-only
   STATUS      optional
   DESCRIPTION "Indicates the maximum number of supported media types. "
   USE ""
   INTERACTION " This object indicates which bits in the MEDIA-NAMES-AVAILABLEobject are significant. "
   OPERATION " Not destructive."
::= { media-types 1 }

-- 1.3.6.1.4.1.11.2.3.9.4.2.1.6.2
channelprinteralert  OBJECT-TYPE
   SYNTAX      binary
   ACCESS      read-only , trappable
   STATUS      optional
   DESCRIPTION "Identifies the values of prtAlertIndex, prtAlertSeverityLevel,prtAlertGroup, prtAlertGroupIndex, prtAlertLocation, andprtAlertCode for the latest critical evnet in theprtAlertTable. The binary string is defined as following: \\&lt;table&gt;-----------------------------------------------------Field  | Filed  | DescriptionOffset | Length |-----------------------------------------------------0    |    4   | the value of prtAlertIndex4    |    4   | the value of prtAlertSeverityLevel8    |    4   | the value of prtAlertGroup12    |    4   | the value of prtAlertGroupIndex16    |    4   | the value of prtAlertLocation20    |    4   | the value of prtAlertCode------------------------------------------------------&lt;/table&gt;\\Each field is in Big Endian style. "
   USE ""
   INTERACTION " MIO cards use this information to create a trap as specified inthe standard printer MIB. The following text describes thetrap: \\printerAlert TRAP-TYPE \\ENTERPRISE printerV1Alert \\VARIABLES { prtAlertIndex, \\prtAlertSeverityLevel, \\prtAlertGroup, prtAlertGroupIndex, \\prtAlertLocation, prtAlertCode } \\ "
   OPERATION " Not destructive."
::= { channel 2 }


-- 1.3.6.1.2.1.25.2.2
hrmemorysize  OBJECT-TYPE
   SYNTAX      INTEGER
   ACCESS      read-only
   STATUS      mandatory
   DESCRIPTION "The amount of physical main memory contained bythe host.Refer to RFC 1514, Host Resources MIB, for more details. "
   USE "  "
   INTERACTION " "
   OPERATION ""
::= { hrStorage 2 }

-- 1.3.6.1.2.1.25.2.3.1.1
hrstorageindex  OBJECT-TYPE
   SYNTAX      INTEGER (1..2147483647)
   ACCESS      read-only
   STATUS      mandatory
   DESCRIPTION "A unique value for each logical storage areacontained by the host.Refer to RFC 1514, Host Resources MIB, for more details. "
   USE "  "
   INTERACTION " "
   OPERATION ""
::= { hrStorageEntry 1 }

-- 1.3.6.1.2.1.25.2.3.1.2
hrstoragetype  OBJECT-TYPE
   SYNTAX      OBJECT IDENTIFIER
   ACCESS      read-only
   STATUS      mandatory
   DESCRIPTION "The type of storage represented by this entry.Refer to RFC 1514, Host Resources MIB, for more details. "
   USE "  "
   INTERACTION " "
   OPERATION ""
::= { hrStorageEntry 2 }

-- 1.3.6.1.2.1.25.2.3.1.3
hrstoragedescr  OBJECT-TYPE
   SYNTAX      binary
   ACCESS      read-only
   STATUS      mandatory
   DESCRIPTION "A description of the type and instance of thestorage described by this entry.Refer to RFC 1514, Host Resources MIB, for more details. "
   USE "  "
   INTERACTION " "
   OPERATION ""
::= { hrStorageEntry 3 }

-- 1.3.6.1.2.1.25.2.3.1.4
hrstorageallocationunits  OBJECT-TYPE
   SYNTAX      INTEGER (1..2147483647)
   ACCESS      read-only
   STATUS      mandatory
   DESCRIPTION "The size, in bytes, of the data objects allocatedfrom this pool.  If this entry is monitoringsectors, blocks, buffers, or packets, for example,this number will commonly be greater than one.Otherwise this number will typically be one.Refer to RFC 1514, Host Resources MIB, for more details. "
   USE "  "
   INTERACTION " "
   OPERATION ""
::= { hrStorageEntry 4 }

-- 1.3.6.1.2.1.25.2.3.1.5
hrstoragesize  OBJECT-TYPE
   SYNTAX      INTEGER (0..2147483647)
   ACCESS      read-write
   STATUS      mandatory
   DESCRIPTION "The size of the storage represented by this entry,in units of hrStorageAllocationUnits.Refer to RFC 1514, Host Resources MIB, for more details. "
   USE "  "
   INTERACTION " "
   OPERATION ""
::= { hrStorageEntry 5 }

-- 1.3.6.1.2.1.25.2.3.1.6
hrstorageused  OBJECT-TYPE
   SYNTAX      INTEGER (0..2147483647)
   ACCESS      read-only
   STATUS      mandatory
   DESCRIPTION "The amount of the storage represented by thisentry that is allocated, in units ofhrStorageAllocationUnits.Refer to RFC 1514, Host Resources MIB, for more details. "
   USE "  "
   INTERACTION " "
   OPERATION ""
::= { hrStorageEntry 6 }

-- 1.3.6.1.2.1.25.2.3.1.7
hrstorageallocationfailures  OBJECT-TYPE
   SYNTAX      INTEGER
   ACCESS      read-only
   STATUS      mandatory
   DESCRIPTION "The number of requests for storage represented bythis entry that could not be honored due to notenough storage.  It should be noted that as thisobject has a SYNTAX of Counter, that it does nothave a defined initial value.  However, it isrecommended that this object be initialized tozero.Refer to RFC 1514, Host Resources MIB, for more details. "
   USE "  "
   INTERACTION " "
   OPERATION ""
::= { hrStorageEntry 7 }

-- 1.3.6.1.2.1.25.3.2.1.1
hrdeviceindex  OBJECT-TYPE
   SYNTAX      INTEGER (1..2147483647)
   ACCESS      read-only
   STATUS      mandatory
   DESCRIPTION "A unique value for each device contained by thehost.  The value for each device must remainconstant at least from one re-initialization of theagent to the next re-initialization.Refer to RFC 1514, Host Resources MIB, for more details. "
   USE "  "
   INTERACTION " "
   OPERATION ""
::= { hrDeviceEntry 1 }

-- 1.3.6.1.2.1.25.3.2.1.2
hrdevicetype  OBJECT-TYPE
   SYNTAX      OBJECT IDENTIFIER
   ACCESS      read-only
   STATUS      mandatory
   DESCRIPTION "An indication of the type of device.If this value is `hrDeviceProcessor { hrDeviceTypes3 }' then an entry exists in the hrProcessorTablewhich corresponds to this device.If this value is `hrDeviceNetwork { hrDeviceTypes 4}', then an entry exists in the hrNetworkTablewhich corresponds to this device.If this value is `hrDevicePrinter { hrDeviceTypes 5}', then an entry exists in the hrPrinterTablewhich corresponds to this device.If this value is `hrDeviceDiskStorage {hrDeviceTypes 6 }', then an entry exists in thehrDiskStorageTable which corresponds to thisdevice.Refer to RFC 1514, Host Resources MIB, for more details. "
   USE "  "
   INTERACTION " "
   OPERATION ""
::= { hrDeviceEntry 2 }

-- 1.3.6.1.2.1.25.3.2.1.3
hrdevicedescr  OBJECT-TYPE
   SYNTAX      binary (SIZE (0..64))
   ACCESS      read-only
   STATUS      mandatory
   DESCRIPTION "A textual description of this device, includingthe device's manufacturer and revision, andoptionally, its serial number.Refer to RFC 1514, Host Resources MIB, for more details. "
   USE "  "
   INTERACTION " "
   OPERATION ""
::= { hrDeviceEntry 3 }

-- 1.3.6.1.2.1.25.3.2.1.4
hrdeviceid  OBJECT-TYPE
   SYNTAX      OBJECT IDENTIFIER
   ACCESS      read-only
   STATUS      mandatory
   DESCRIPTION "The product ID for this device.Refer to RFC 1514, Host Resources MIB, for more details. "
   USE "  "
   INTERACTION " "
   OPERATION ""
::= { hrDeviceEntry 4 }

-- 1.3.6.1.2.1.25.3.2.1.5
hrdevicestatus  OBJECT-TYPE
   SYNTAX      enumerated { eHunknown (1) , eHrunning (2) , eHwarning (3) , eHtesting (4) , eHdown (5) }
   ACCESS      read-only
   STATUS      mandatory
   DESCRIPTION "The current operational state of the devicedescribed by this row of the table.  A valueunknown(1) indicates that the current state of thedevice is unknown.  running(2) indicates that thedevice is up and running and that no unusual errorconditions are known.  The warning(3) stateindicates that agent has been informed of anunusual error condition by the operational software(e.g., a disk device driver) but that the device isstill 'operational'.  An example would be highnumber of soft errors on a disk.  A value oftesting(4), indicates that the device is notavailable for use because it is in the testingstate.  The state of down(5) is used only when theagent has been informed that the device is notavailable for any use.Refer to RFC 1514, Host Resources MIB, for more details. "
   USE "  "
   INTERACTION " "
   OPERATION ""
::= { hrDeviceEntry 5 }

-- 1.3.6.1.2.1.25.3.2.1.6
hrdeviceerrors  OBJECT-TYPE
   SYNTAX      INTEGER
   ACCESS      read-only
   STATUS      mandatory
   DESCRIPTION "The number of errors detected on this device.  Itshould be noted that as this object has a SYNTAXof Counter, that it does not have a definedinitial value.  However, it is recommended thatthis object be initialized to zero.Refer to RFC 1514, Host Resources MIB, for more details. "
   USE "  "
   INTERACTION " "
   OPERATION ""
::= { hrDeviceEntry 6 }

-- 1.3.6.1.2.1.25.3.6.1.1
hrdiskstorageaccess  OBJECT-TYPE
   SYNTAX      enumerated { eHreadWrite (1) , eHreadOnly (2) }
   ACCESS      read-only
   STATUS      mandatory
   DESCRIPTION "An indication if this long-term storage device isreadable and writable or only readable.  Thisshould reflect the media type, any write-protectmechanism, and any device configuration thataffects the entire device.Refer to RFC 1514, Host Resources MIB, for more details. "
   USE "  "
   INTERACTION " "
   OPERATION ""
::= { hrDiskStorageEntry 1 }

-- 1.3.6.1.2.1.25.3.6.1.2
hrdiskstoragemedia  OBJECT-TYPE
   SYNTAX      enumerated { eHother (1) , eHunknown (2) , eHhardDisk (3) , eHfloppyDisk (4) , eHopticalDiskROM (5) , eHopticalDiskWORM (6) , eHopticalDiskRW (7) , eHramDisk (8) }
   ACCESS      read-only
   STATUS      mandatory
   DESCRIPTION "An indication of the type of media used in thislong-term storage device.Refer to RFC 1514, Host Resources MIB, for more details. "
   USE "  "
   INTERACTION " "
   OPERATION ""
::= { hrDiskStorageEntry 2 }

-- 1.3.6.1.2.1.25.3.6.1.3
hrdiskstorageremoveble  OBJECT-TYPE
   SYNTAX      enumerated { eHtrue (1) , eHfalse (2) }
   ACCESS      read-only
   STATUS      mandatory
   DESCRIPTION "Denotes whether or not the disk media may beremoved from the drive.Refer to RFC 1514, Host Resources MIB, for more details. "
   USE "  "
   INTERACTION " "
   OPERATION ""
::= { hrDiskStorageEntry 3 }

-- 1.3.6.1.2.1.25.3.6.1.4
hrdiskstoragecapacity  OBJECT-TYPE
   SYNTAX      INTEGER
   ACCESS      read-only
   STATUS      mandatory
   DESCRIPTION "The total size for this long-term storage device.Refer to RFC 1514, Host Resources MIB, for more details. "
   USE "  "
   INTERACTION " "
   OPERATION ""
::= { hrDiskStorageEntry 4 }

-- 1.3.6.1.2.1.25.3.8.1.1
hrfsindex  OBJECT-TYPE
   SYNTAX      INTEGER (1..2147483647)
   ACCESS      read-only
   STATUS      mandatory
   DESCRIPTION "A unique value for each file device-system local to thishost.  The value for each file device-system must remainconstant at least from one re-initialization ofthe agent to the next re-initialization.Refer to RFC 1514, Host Resources MIB, for more details. "
   USE "  "
   INTERACTION " "
   OPERATION ""
::= { hrFSEntry 1 }

-- 1.3.6.1.2.1.25.3.8.1.2
hrfsmountpoint  OBJECT-TYPE
   SYNTAX      binary
   ACCESS      read-only
   STATUS      mandatory
   DESCRIPTION "The path name of the root of this file system.Refer to RFC 1514, Host Resources MIB, for more details. "
   USE "  "
   INTERACTION " "
   OPERATION ""
::= { hrFSEntry 2 }

-- 1.3.6.1.2.1.25.3.8.1.3
hrfsremotemountpoint  OBJECT-TYPE
   SYNTAX      binary
   ACCESS      read-only
   STATUS      mandatory
   DESCRIPTION "A description of the name and/or address of theserver that this file device-system is mounted from.This may also include parameters such as the mountpoint on the remote file system.  If this is not aremote file system, this string should have alength of zero.Refer to RFC 1514, Host Resources MIB, for more details. "
   USE "  "
   INTERACTION " "
   OPERATION ""
::= { hrFSEntry 3 }

-- 1.3.6.1.2.1.25.3.8.1.4
hrfstype  OBJECT-TYPE
   SYNTAX      OBJECT IDENTIFIER
   ACCESS      read-only
   STATUS      mandatory
   DESCRIPTION "The value of this object identifies the type ofthis file system.Refer to RFC 1514, Host Resources MIB, for more details. "
   USE "  "
   INTERACTION " "
   OPERATION ""
::= { hrFSEntry 4 }

-- 1.3.6.1.2.1.25.3.8.1.5
hrfsaccess  OBJECT-TYPE
   SYNTAX      enumerated { eHreadWrite (1) , eHreadOnly (2) }
   ACCESS      read-only
   STATUS      mandatory
   DESCRIPTION "An indication if this file device-system is logicallyconfigured by the operating device-system to be readableand writable or only readable.  This does notrepresent any local access-control policy, exceptone that is applied to the file device-system as a whole.Refer to RFC 1514, Host Resources MIB, for more details. "
   USE "  "
   INTERACTION " "
   OPERATION ""
::= { hrFSEntry 5 }

-- 1.3.6.1.2.1.25.3.8.1.6
hrfsbootable  OBJECT-TYPE
   SYNTAX      enumerated { eHtrue (1) , eHfalse (2) }
   ACCESS      read-only
   STATUS      mandatory
   DESCRIPTION "A flag indicating whether this file device-system isbootable.Refer to RFC 1514, Host Resources MIB, for more details. "
   USE "  "
   INTERACTION " "
   OPERATION ""
::= { hrFSEntry 6 }

-- 1.3.6.1.2.1.25.3.8.1.7
hrfsstorageindex  OBJECT-TYPE
   SYNTAX      INTEGER (0..2147483647)
   ACCESS      read-only
   STATUS      mandatory
   DESCRIPTION "The index of the hrStorageEntry that representsinformation about this file system.  If there isno such information available, then this valueshall be zero.  The relevant storage entry will beuseful in tracking the percent usage of this filesystem and diagnosing errors that may occur whenit runs out of space.Refer to RFC 1514, Host Resources MIB, for more details. "
   USE "  "
   INTERACTION " "
   OPERATION ""
::= { hrFSEntry 7 }

-- 1.3.6.1.2.1.25.3.8.1.8
hrfslastfullbackupdate  OBJECT-TYPE
   SYNTAX      binary
   ACCESS      read-write
   STATUS      mandatory
   DESCRIPTION "The last date at which this complete file systemwas copied to another storage device for backup.This information is useful for ensuring thatbackups are being performed regularly.If this information is not known, then thisvariable shall have the value corresponding toJanuary 1, year 0000, 00:00:00.0, which is encodedas (hex)'00 00 01 01 00 00 00 00'.Refer to RFC 1514, Host Resources MIB, for more details. "
   USE "  "
   INTERACTION " "
   OPERATION ""
::= { hrFSEntry 8 }

-- 1.3.6.1.2.1.25.3.8.1.9
hrfslastpartialbackupdate  OBJECT-TYPE
   SYNTAX      binary
   ACCESS      read-write
   STATUS      mandatory
   DESCRIPTION "The last date at which a portion of this filesystem was copied to another storage device forbackup.  This information is useful for ensuringthat backups are being performed regularly.If this information is not known, then thisvariable shall have the value corresponding toJanuary 1, year 0000, 00:00:00.0, which is encodedas (hex)'00 00 01 01 00 00 00 00'.Refer to RFC 1514, Host Resources MIB, for more details. "
   USE "  "
   INTERACTION " "
   OPERATION ""
::= { hrFSEntry 9 }

-- 1.3.6.1.2.1.43.11.1.1.2
prtmarkersuppliesmarkerindex  OBJECT-TYPE
   SYNTAX      INTEGER (0..65535)
   ACCESS      read-only
   STATUS      optional
   DESCRIPTION "The value of prtMarkerIndex corresponding to themarking sub-unit with which this marker supplysub-unit is associated. "
   USE "  "
   INTERACTION " "
   OPERATION ""
   ::= { prtMarkerSuppliesEntry 2 }

-- 1.3.6.1.2.1.43.11.1.1.3
prtmarkersuppliescolorantindex  OBJECT-TYPE
   SYNTAX      INTEGER (0..65535)
   ACCESS      read-only
   STATUS      optional
   DESCRIPTION "The value of prtMarkerColorantIndexcorresponding to the colorant with which thismarker supply sub-unit is associated.  This valueshall be 0 if there is no colorant table. "
   USE "  "
   INTERACTION " "
   OPERATION ""
   ::= { prtMarkerSuppliesEntry 3 }

-- 1.3.6.1.2.1.43.11.1.1.4
prtmarkersuppliesclass  OBJECT-TYPE
   SYNTAX      enumerated { ePother (1) , ePsupplyThatIsConsumed (3) , ePreceptacleThatIsFilled (4) }
   ACCESS      read-only
   STATUS      optional
   DESCRIPTION "Indicates whether this supply entity represents a supplythat is consumed or a receptacle that is filled. "
   USE "  "
   INTERACTION " "
   OPERATION ""
   ::= { prtMarkerSuppliesEntry 4 }

-- 1.3.6.1.2.1.43.11.1.1.5
prtmarkersuppliestype  OBJECT-TYPE
   SYNTAX      enumerated { ePother (1) , ePunknown (2) , ePtoner (3) , ePwasteToner (4) , ePink (5) , ePinkCartridge (6) , ePinkRibbon (7) , ePwasteInk (8) , ePopc (9) , ePdeveloper (10) , ePfuserOil (11) , ePsolidWax (12) , ePribbonWax (13) , ePwasteWax (14) , ePfuser (15) , ePcoronaWire (16) , ePfuserOilWick (17) , ePcleanerUnit (18) , ePfuserCleaningPad (19) , ePtransferUnit (20) , ePtonerCartridge (21) , ePfuserOiler (22) , ePadfmaintkit (23) , ePfixer (24) }
   ACCESS      read-only
   STATUS      optional
   DESCRIPTION "The type of this supply. "
   USE "  "
   INTERACTION " "
   OPERATION ""
   ::= { prtMarkerSuppliesEntry 5 }

-- 1.3.6.1.2.1.43.11.1.1.6
prtmarkersuppliesdescription  OBJECT-TYPE
   SYNTAX      binary (SIZE (0..255))
   ACCESS      read-only
   STATUS      optional
   DESCRIPTION "The description of this supply container/receptacle in thelocalization specified by prtGeneralCurrentLocalization. "
   USE "  "
   INTERACTION " "
   OPERATION ""
   ::= { prtMarkerSuppliesEntry 6 }

-- 1.3.6.1.2.1.43.11.1.1.7
prtmarkersuppliessupplyunit  OBJECT-TYPE
   SYNTAX      enumerated { ePtenThousandthsOfInches (3) , ePmicrometers (4) , ePimpressions (7) , ePsheets (8) , ePthousandthsOfOunces (12) , ePhours (11) , ePtenthsOfGrams (13) , ePhundrethsOfFluidOunces (14) , ePtenthsOfMilliliters (15) , ePfeet (16) , ePmeters (17) , ePpercent (19) }
   ACCESS      read-only
   STATUS      optional
   DESCRIPTION "Unit of measure of this marker supply container/receptacle. "
   USE "  "
   INTERACTION " "
   OPERATION ""
   ::= { prtMarkerSuppliesEntry 7 }

-- 1.3.6.1.2.1.43.11.1.1.8
prtmarkersuppliesmaxcapacity  OBJECT-TYPE
   SYNTAX      INTEGER
   ACCESS      read-write
   STATUS      optional
   DESCRIPTION "The maximum capacity of this supply container/receptacleexpressed in prtMarkerSuppliesSupplyUnit. If this supplycontainer/receptacle can reliably sense this value, thevalue is reported by the printer and is read-only;otherwise, the value may be written (by a Remote ControlPanel or a Management Application). The value (-1) meansother and specifically indicates that the sub-unit placesno restrictions on this parameter. The value (-2) meansunknown. "
   USE "  "
   INTERACTION " "
   OPERATION ""
   ::= { prtMarkerSuppliesEntry 8 }

-- 1.3.6.1.2.1.43.11.1.1.9
prtmarkersupplieslevel  OBJECT-TYPE
   SYNTAX      INTEGER
   ACCESS      read-write
   STATUS      optional
   DESCRIPTION "The current level if this supply is a container; theremaining space if this supply is a receptacle. If thissupply container/receptacle can reliably sense thisvalue, the value is reported by the printer and isread-only; otherwise, the value may be written (by aRemote Control Panel or a Management Application). Thevalue (-1) means other and specifically indicates thatthe sub-unit places no restrictions on this parameter.The value (-2) means unknown.  A value of (-3) means that theprinter knows that there is some supply/remaining space,respectively. "
   USE "  "
   INTERACTION " "
   OPERATION ""
   ::= { prtMarkerSuppliesEntry 9 }

-- 1.3.6.1.2.1.43.12.1.1.2
prtmarkercolorantmarkerindex  OBJECT-TYPE
   SYNTAX      INTEGER (0..65535)
   ACCESS      read-only
   STATUS      optional
   DESCRIPTION "The value of prtMarkerIndex corresponding to themarker sub-unit with which this colorant entry isassociated. "
   USE "  "
   INTERACTION " "
   OPERATION ""
   ::= { prtMarkerColorantEntry 2 }

-- 1.3.6.1.2.1.43.12.1.1.3
prtmarkercolorantrole  OBJECT-TYPE
   SYNTAX      enumerated { ePother (1) , ePprocess (3) , ePspot (4) }
   ACCESS      read-only
   STATUS      optional
   DESCRIPTION "The role played by this colorant. "
   USE "  "
   INTERACTION " "
   OPERATION ""
   ::= { prtMarkerColorantEntry 3 }

-- 1.3.6.1.2.1.43.12.1.1.4
prtmarkercolorantvalue  OBJECT-TYPE
   SYNTAX      binary (SIZE (0..255))
   ACCESS      read-only
   STATUS      optional
   DESCRIPTION "The name of the color of thiscolorant using standardized string names from ISO 10175 (DPA)and ISO 10180 (SPDL) which are:otherunknownwhiteredgreenbluecyanmagentayellowblackImplementors may add additional string values. The namingconventions in ISO 9070 are recommended in order to avoidpotential name clashes. "
   USE "  "
   INTERACTION " "
   OPERATION ""
   ::= { prtMarkerColorantEntry 4 }

-- 1.3.6.1.2.1.43.13.4.1.11
prtmediapathstatus  OBJECT-TYPE
   SYNTAX      INTEGER
   ACCESS      read-only
   STATUS      optional
   DESCRIPTION "The current status of this media path. "
   USE "  "
   INTERACTION " "
   OPERATION ""
   ::= { printmib 14 }

-- 1.3.6.1.2.1.43.15.1.1.2
prtinterpreterlangfamily  OBJECT-TYPE
   SYNTAX      enumerated { ePother (1) , ePlangPCL (3) , ePlangHPGL (4) , ePlangPJL (5) , ePlangPS (6) , ePlangIPDS (7) , ePlangPPDS (8) , ePlangEscapeP (9) , ePlangEpson (10) , ePlangDDIF (11) , ePlangInterpress (12) , ePlangISO6429 (13) , ePlangLineData (14) , ePlangMODCA (15) , ePlangREGIS (16) , ePlangSCS (17) , ePlangSPDL (18) , ePlangTEK4014 (19) , ePlangPDS (20) , ePlangIGP (21) , ePlangCodeV (22) , ePlangDSCDSE (23) , ePlangWPS (24) , ePlangLN03 (25) , ePlangCCITT (26) , ePlangQUIC (27) , ePlangCPAP (28) , ePlangDecPPL (29) , ePlangSimpleText (30) , ePlangNPAP (31) , ePlangDOC (32) , ePlangimPress (33) , ePlangPinwriter (34) , ePlangNPDL (35) , ePlangNEC201PL (36) , ePlangAutomatic (37) , ePlangPages (38) , ePlangLIPS (39) , ePlangTIFF (40) , ePlangDiagnostic (41) , ePlangPSPrinter (42) , ePlangCaPSL (43) , ePlangEXCL (44) , ePlangLCDS (45) , ePlangXES (46) , ePlangPCLXL (47) , ePlangART (48) , ePlangTIPSI (49) , ePlangPrescribe (50) , ePlangLinePrinter (51) , ePlangIDP (52) , ePLangXJCL (53) , ePlangPDF (54) , ePlangRPDL (55) , ePlangIntermedIPL (56) , ePlangUBIFingerprint (57) , ePlangUBIDirectProtocol (58) , ePlangXPS (59) , ePlangURP (60) , ePlangFAXPDL (201) }
   ACCESS      read-only
   STATUS      optional
   DESCRIPTION "The family name of a Page Description Language (PDL) orcontrol language which this interpreter in the printer caninterpret or emulate. "
   USE "  "
   INTERACTION " "
   OPERATION ""
   ::= { prtInterpreterEntry 2 }

-- 1.3.6.1.2.1.43.15.1.1.3
prtinterpreterlanglevel  OBJECT-TYPE
   SYNTAX      binary (SIZE (0..31))
   ACCESS      read-only
   STATUS      optional
   DESCRIPTION "The level of the language which this interpreter isinterpreting or emulating.  This might contain a value like'5e' for an interpreter which is emulating level 5e of the PCLlanguage.  It might contain '2' for an interpreter which isemulating level 2 of the PostScript language.  Similarly itmight contain '2' for an interpreter which is emulating level2 of the HPGL language. "
   USE "  "
   INTERACTION " "
   OPERATION ""
   ::= { prtInterpreterEntry 3 }

-- 1.3.6.1.2.1.43.15.1.1.5
prtinterpreterdescription  OBJECT-TYPE
   SYNTAX      binary (SIZE (0..255))
   ACCESS      read-only
   STATUS      optional
   DESCRIPTION "A string to identify this interpreter in the localizationspecified by prtGeneralCurrentLocalization as opposed to thelanguage which is being interpreted.  It is anticipated thatthis string will allow manufacturers to unambiguously identifytheir interpreters. "
   USE "  "
   INTERACTION " "
   OPERATION ""
   ::= { prtInterpreterEntry 5 }

-- 1.3.6.1.2.1.43.18.1.1.2
prtalertseveritylevel  OBJECT-TYPE
   SYNTAX      enumerated { ePother (1) , ePcriticalBinaryChangeEvent (3) , ePwarningUnaryChangeEvent (4) , ePwarningBinaryChangeEvent (5) }
   ACCESS      read-only
   STATUS      optional
   DESCRIPTION "The level of severity of this alert table entry.  The printerdetermines the severity level assigned to each entry into thetable. "
   USE "  "
   INTERACTION " "
   OPERATION ""
   ::= { prtAlertEntry 2 }

-- 1.3.6.1.2.1.43.18.1.1.3
prtalerttraininglevel  OBJECT-TYPE
   SYNTAX      enumerated { ePother (1) , ePunknown (2) , ePuntrained (3) , ePtrained (4) , ePfieldService (5) , ePmanagement (6) , ePnoInterventionRequired (7) }
   ACCESS      read-only
   STATUS      optional
   DESCRIPTION "See textual convention PrtAlertTrainingLevelTC "
   USE "  "
   INTERACTION " "
   OPERATION ""
   ::= { prtAlertEntry 3 }

-- 1.3.6.1.2.1.43.18.1.1.4
prtalertgroup  OBJECT-TYPE
   SYNTAX      enumerated { ePother (1) , ePhostResourcesMIBStorageTable (3) , ePhostResourcesMIBDeviceTable (4) , ePgeneralPrinter (5) , ePcover (6) , ePlocalization (7) , ePinput (8) , ePoutput (9) , ePmarker (10) , ePmarkerSupplies (11) , ePmarkerColorant (12) , ePmediaPath (13) , ePchannel (14) , ePinterpreter (15) , ePconsoleDisplayBuffer (16) , ePconsoleLights (17) , ePalert (18) }
   ACCESS      read-only
   STATUS      optional
   DESCRIPTION "The type of sub-unit within the printer model that this alertis related.  Input, output, and markers are examples ofprinter model groups, i.e., examples of types of sub-units.Wherever possible, these enumerations match thesub-identifier that identifies the relevant table in theprintmib. "
   USE "  "
   INTERACTION " "
   OPERATION ""
   ::= { prtAlertEntry 4 }

-- 1.3.6.1.2.1.43.18.1.1.5
prtalertgroupindex  OBJECT-TYPE
   SYNTAX      INTEGER
   ACCESS      read-only
   STATUS      optional
   DESCRIPTION "An index of the row within the principle table in thegroup identified by prtAlertGroup that represents thesub-unit of the printer that caused this alert.  Thecombination of the prtAlertGroup and the prtAlertGroupIndex definesexactly which printer sub-unit caused the alert.; forexample, Input #3, Output #2, and Marker #1.Every object in this MIB is indexed with hrDeviceIndex andoptionally, another index variable.  If this other indexvariable is present in the table that generated the alert, itwill be used as the value for this object.  Otherwise, thisvalue shall be -1. "
   USE "  "
   INTERACTION " "
   OPERATION ""
   ::= { prtAlertEntry 5 }

-- 1.3.6.1.2.1.43.18.1.1.6
prtalertlocation  OBJECT-TYPE
   SYNTAX      INTEGER
   ACCESS      read-only
   STATUS      optional
   DESCRIPTION "The sub-unit location that is defined by the printermanufacturer to further refine the location of this alertwithin the designated sub-unit.  The location is used inconjunction with the Group and GroupIndex values; forexample, there is an alert in Input #2 at location number 7.The value (-2) indicates unknown "
   USE "  "
   INTERACTION " "
   OPERATION ""
   ::= { prtAlertEntry 6 }

-- 1.3.6.1.2.1.43.18.1.1.7
prtalertcode  OBJECT-TYPE
   SYNTAX      enumerated { ePother (1) , ePunknown (2) , ePcoverOpened (3) , ePcoverClosed (4) , ePinterlockOpened (5) , ePinterlockClosed (6) , ePconfigurationChanged (7) , ePjammed (8) , ePsubunitMissing (9) , ePsubunitLifeAlmostOver (10) , ePsubunitLifeOver (11) , ePsubunitAlmostEmpty (12) , ePsubunitEmpty (13) , ePsubunitAlmostFull (14) , ePsubunitFull (15) , ePsubunitNearLimit (16) , ePsubunitAtLimit (17) , ePsubunitOpened (18) , ePsubunitClosed (19) , ePsubunitTurnedOn (20) , ePsubunitTurnedOff (21) , ePsubunitOffline (22) , ePsubunitPowerSaver (23) , ePsubunitWarmingUp (24) , ePsubunitAdded (25) , ePsubunitRemoved (26) , ePsubunitResourceAdded (27) , ePsubunitResourceRemoved (28) , ePsubunitRecoverableFailure (29) , ePsubunitUnrecoverableFailure (30) , ePsubunitRecoverableStorageError (31) , ePsubunitUnrecoverableStorageError (32) , ePsubunitMotorFailure (33) , ePsubunitMemoryExhausted (34) , ePcoverOpened (501) , ePcoverClosed (502) , ePpoweredUp (503) , ePpoweredDown (504) , ePprinterNMSReset (505) , ePprinterManualReset (506) , ePprinterReadyToPrint (507) , ePJobAccountingRingBufferFull (508) , ePinputMediaTrayMissing (801) , ePinputMediaSizeChanged (802) , ePinputMediaWeightChanged (803) , ePinputMediaTypeChanged (804) , ePinputMediaColorChanged (805) , ePinputMediaFormPartsChange (806) , ePinputMediaSupplyLow (807) , ePinputMediaSupplyEmpty (808) , ePinputMediaChangeRequest (809) , ePinputManualInputRequest (810) , ePinputTrayPositionFailure (811) , ePinputTrayElevationFailure (812) , ePinputCannotFeedSizeSelected (813) , ePoutputMediaTrayMissing (901) , ePoutputMediaTrayAlmostFull (902) , ePoutputMediaTrayFull (903) , ePoutputMailboxSelectFailure (904) , ePmarkerFuserUnderTemperature (1001) , ePmarkerFuserOverTemperature (1002) , ePmarkerFuserTimingFailure (1003) , ePmarkerFuserThermistorFailure (1004) , ePmarkerAdjustingPrintQuality (1005) , ePmarkerTonerEmpty (1101) , ePmarkerInkEmpty (1102) , ePmarkerPrintRibbonEmpty (1103) , ePmarkerTonerAlmostEmpty (1104) , ePmarkerInkAlmostEmpty (1105) , ePmarkerPrintRibbonAlmostEmpty (1106) , ePmarkerWasteTonerReceptacleAlmostFull (1107) , ePmarkerWasteInkReceptacleAlmostFull (1108) , ePmarkerWasteTonerReceptacleFull (1109) , ePmarkerWasteInkReceptacleFull (1110) , ePmarkerOpcLifeAlmostOver (1111) , ePmarkerOpcLifeOver (1112) , ePmarkerDeveloperAlmostEmpty (1113) , ePmarkerDeveloperEmpty (1114) , ePmarkerTonerCartridgeMissing (1115) , ePmediaPathMediaTrayMissing (1301) , ePmediaPathMediaTrayAlmostFull (1302) , ePmediaPathMediaTrayFull (1303) , ePinterpreterMemoryIncreased (1501) , ePinterpreterMemoryDecreased (1502) , ePinterpreterCartridgeAdded (1503) , ePinterpreterCartridgeDeleted (1504) , ePinterpreterResourceAdded (1505) , ePinterpreterResourceDeleted (1506) , ePinterpreterResourceUnavailable (1507) , ePinterpreterComplexPageEncountered (1509) , ePalertRemovalOfBinaryChangeEntry (1801) }
   ACCESS      read-only
   STATUS      optional
   DESCRIPTION "See associated textual convention PrtAlertCodeTC "
   USE "  "
   INTERACTION " "
   OPERATION ""
   ::= { prtAlertEntry 8 }

-- 1.3.6.1.2.1.43.18.1.1.8
prtalertdescription  OBJECT-TYPE
   SYNTAX      binary (SIZE (0..255))
   ACCESS      read-only
   STATUS      optional
   DESCRIPTION "A description of this alert entry in the localizationspecified by prtGeneralCurrentLocalization.  The description isprovided by the printer to further elaborate on the enumeratedalert or provide information in the case where the code isclassified as `other' or `unknown'.  The printer is requiredto return a description string but the string may be a nullstring. "
   USE "  "
   INTERACTION " "
   OPERATION ""
   ::= { prtAlertEntry 8 }

-- 1.3.6.1.2.1.43.18.1.1.9
prtalerttime  OBJECT-TYPE
   SYNTAX      INTEGER (0..4294967295)
   ACCESS      read-only
   STATUS      optional
   DESCRIPTION "The value of sysUpTime at the time that this alert wasgenerated. "
   USE "  "
   INTERACTION " "
   OPERATION ""
   ::= { prtAlertEntry 9 }

-- 1.3.6.1.2.1.43.7.1.1.2
prtlocalizationlanguage  OBJECT-TYPE
   SYNTAX      binary (SIZE (0..2))
   ACCESS      read-only
   STATUS      optional
   DESCRIPTION "A two character language code from ISO 639.  Examplesen, gb, ca, fr, de. "
   USE "  "
   INTERACTION " "
   OPERATION ""
   ::= { prtLocalizationEntry 2 }

-- 1.3.6.1.2.1.43.7.1.1.3
prtlocalizationcountry  OBJECT-TYPE
   SYNTAX      binary (SIZE (0..2))
   ACCESS      read-only
   STATUS      optional
   DESCRIPTION "A two character country code from ISO 3166, a blank string(two space characters) shall indicate that the country isnot defined.  Examples: US, FR, DE, ... "
   USE "  "
   INTERACTION " "
   OPERATION ""
   ::= { prtLocalizationEntry 3 }

-- 1.3.6.1.2.1.43.7.1.1.4
prtlocalizationcharacterset  OBJECT-TYPE
   SYNTAX      enumerated { ePother (1) , ePcsASCII (3) , ePcsUnicode (1000) , ePcsUCS4 (1001) , ePcsISO10646UTF1 (27) , ePcsISO646basic1983 (28) , ePcsINVARIANT (29) , ePcsISO2IntlRefVersion (30) , ePcsISO4UnitedKingdom (20) , ePcsNATSSEFI (31) , ePcsNATSSEFIADD (32) , ePcsNATSDANO (33) , ePcsNATSDANOADD (34) , ePcsISO10Swedish (35) , ePcsISO11SwedishForNames (21) , ePcsKSC56011987 (36) , ePcsISO2022KR (37) , ePcsEUCKR (38) , ePcsISO2022JP (39) , ePcsISO2022JP2 (40) , ePcsISO13JISC6220jp (41) , ePcsISO14JISC6220ro (42) , ePcsISO15Italian (22) , ePcsISO16Portuguese (43) , ePcsISO17Spanish (23) , ePcsISO18Greek7Old (44) , ePcsISO19LatinGreek (45) , ePcsISO21German (24) , ePcsISO25French (46) , ePcsISO27LatinGreek1 (47) , ePcsISO5427Cyrillic (48) , ePcsISO42JISC62261978 (49) , ePcsISO47BSViewdata (50) , ePcsISO49INIS (51) , ePcsISO50INIS8 (52) , ePcsISO51INISCyrillic (53) , ePcsISO5428Greek (55) , ePcsISO57GB1988 (56) , ePcsISO58GB231280 (57) , ePcsISO60DanishNorwegian (25) , ePcsISO61Norwegian2 (58) , ePcsISO69French (26) , ePcsISO70VideotexSupp1 (59) , ePcsISO84Portuguese2 (60) , ePcsISO85Spanish2 (61) , ePcsISO86Hungarian (62) , ePcsISO87JISX0208 (63) , ePcsISO88Greek7 (64) , ePcsISO89ASMO449 (65) , ePcsISO90 (66) , ePcsISO91JISC62291984a (67) , ePcsISO92JISC62991984b (68) , ePcsISO93JIS62291984badd (69) , ePcsISO94JIS62291984hand (70) , ePcsISO95JIS62291984handadd (71) , ePcsISO96JISC62291984kana (72) , ePcsISO2033 (73) , ePcsISO99NAPLPS (74) , ePcsISOLatin1 (4) , ePcsISOLatin2 (5) , ePcsISO102T617bit (75) , ePcsISO103T618bit (76) , ePcsISOLatin3 (6) , ePcsISOLatin4 (7) , ePcsISO111ECMACyrillic (77) , ePcsa7-1 (78) , ePcsa7-2 (79) , ePcsISO123CSAZ24341985gr (80) , ePcsISOLatinArabic (9) , ePcsISO88596E (81) , ePcsISO88596I (82) , ePcsISOLatinGreek (10) , ePcsISO128T101G2 (83) , ePcsISOLatinHebrew (11) , ePcsISO88598E (84) , ePcsISO88598I (85) , ePcsISO139CSN369103 (86) , ePcsISO141JUSIB1002 (87) , ePcsISOTextComm (14) , ePcsISO143IECP271 (88) , ePcsISOLatinCyrillic (8) , ePcsISO146Serbian (89) , ePcsISO147Macedonian (90) , ePcsISOLatin5 (12) , ePcsISO150 (91) , ePcsISO151Cuba (92) , ePcsISO6937Add (93) , ePcsISO153GOST1976874 (94) , ePcsISO8859Supp (95) , ePcsISO10367Box (96) , ePcsISOLatin6 (13) , ePcsISO158Lap (97) , ePcsISO159JISX02121990 (98) , ePcsISO646Danish (99) , ePcsUSDK (100) , ePcsDKUS (101) , ePcsHalfWidthKatakana (15) , ePcsKSC5636 (102) , ePcsDECMCS (2008) , ePcsHPRoman8 (2004) , ePcsMacintosh (2027) , ePcsIBM037 (2028) , ePcsIBM038 (2029) , ePcsIBM273 (2030) , ePcsIBM274 (2031) , ePcsIBM275 (2032) , ePcsIBM277 (2033) , ePcsIBM278 (2034) , ePcsIBM280 (2035) , ePcsIBM281 (2036) , ePcsIBM284 (2037) , ePcsIBM285 (2038) , ePcsIBM290 (2039) , ePcsIBM297 (2040) , ePcsIBM420 (2041) , ePcsIBM423 (2042) , ePcsIBM424 (2043) , ePcsPC8CodePage437 (2011) , ePcsIBM500 (2044) , ePcsPC850Multilingual (2009) , ePcsIBM851 (2045) , ePcsPCp852 (2010) , ePcsIBM855 (2046) , ePcsIBM857 (2047) , ePcsIBM860 (2048) , ePcsIBM861 (2049) , ePcsPC862LatinHebrew (2013) , ePcsIBM863 (2050) , ePcsIBM864 (2051) , ePcsIBM865 (2052) , ePcsIBM868 (2053) , ePcsIBM869 (2054) , ePcsIBM870 (2055) , ePcsIBM871 (2056) , ePcsIBM880 (2057) , ePcsIBM891 (2058) , ePcsIBM903 (2059) , ePcsIBBM904 (2060) , ePcsIBM905 (2061) , ePcsIBM918 (2062) , ePcsIBM1026 (2063) , ePcsIBMEBCDICATDE (2064) , ePcsEBCDICATDEA (2065) , ePcsEBCDICCAFR (2066) , ePcsEBCDICDKNO (2067) , ePcsEBCDICDKNOA (2068) , ePcsEBCDICFISE (2069) , ePcsEBCDICFISEA (2070) , ePcsEBCDICFR (2071) , ePcsEBCDICIT (2072) , ePcsEBCDICES (2074) , ePcsEBCDICESA (2075) , ePcsEBCDICESS (2076) , ePcsEBCDICUK (2077) , ePcsEBCDICUS (2078) , ePcsUnknown8BiT (2079) , ePcsMnemonic (2080) , ePcsMnem (2081) , ePcsVISCII (2082) , ePcsVIQR (2083) , ePcsKOI8R (2084) , ePcsUnicode11 (1010) , ePcsUnicode11UTF7 (103) , ePcsJISEncoding (16) , ePcsShiftJIS (17) , ePcsEUCPkdFmtJapanese (18) , ePcsEUCFixWidJapanese (19) , ePcsUnicodeASCII (1002) , ePcsUnicodeLatin1 (1003) , ePcsUnicodeIBM2039 (1004) , ePcsUnicodeIBM1261 (1005) , ePcsUnidoceIBM1268 (1006) , ePcsUnicodeIBM1276 (1007) , ePcsUnicodeIBM1264 (1008) , ePcsUnicodeIBM1265 (1009) , ePcsUTF8 (1011) , ePcsWindows30Latin1 (2000) , ePcsWindows31Latin1 (2001) , ePcsWindows31Latin2 (2002) , ePcsWindows31Latin5 (2003) , ePcsAdobeStandardEncoding (2005) , ePcsVenturaUS (2006) , ePcsVenturaInternational (2007) , ePcsPC8DanishNorwegian (2012) , ePcsPC8Turkish (2014) , ePcsIBMSymbols (2015) , ePcsIBMThai (2016) , ePcsHPLegal (2017) , ePcsHPPiFont (2018) , ePcsHPMath8 (2019) , ePcsHPPSMath (2020) , ePcsHPDesktop (2021) , ePcsVenturaMath (2022) , ePcsMicrosoftPublishing (2023) , ePcsWindows31J (2024) , ePcsGB2312 (2025) , ePcsBig5 (2026) }
   ACCESS      read-only
   STATUS      optional
   DESCRIPTION "The coded character set used for this localization. "
   USE "  "
   INTERACTION " "
   OPERATION ""
   ::= { prtLocalizationEntry 4 }

-- 1.3.6.1.2.1.43.8.2.1.10
prtinputcurrentlevel  OBJECT-TYPE
   SYNTAX      INTEGER
   ACCESS      read-write
   STATUS      optional
   DESCRIPTION "The current capacity of the input sub-unit in inputsub-unit capacity units (PrtCapacityUnitTC). If this inputsub-unit can reliably sense this value, the value issensed by the printer and may not be changed bymanagement requests; otherwise, the value maybe written (by a Remote Contol Panel or aManagement Application).  The value (-1) means other andspecifically indicates that the sub-unit places norestrictions on this parameter. The value (-2) means unknown.The value (-3) means that the printer knows that at least oneunit remains. "
   USE "  "
   INTERACTION " "
   OPERATION ""
   ::= { prtInputEntry 10 }

-- 1.3.6.1.2.1.43.8.2.1.11
prtinputstatus  OBJECT-TYPE
   SYNTAX      INTEGER
   ACCESS      read-only
   STATUS      optional
   DESCRIPTION "The current status of this input sub-unit. "
   USE "  "
   INTERACTION " "
   OPERATION ""
   ::= { prtInputEntry 11 }

-- 1.3.6.1.2.1.43.8.2.1.12
prtinputmedianame  OBJECT-TYPE
   SYNTAX      binary (SIZE (0..63))
   ACCESS      read-write
   STATUS      optional
   DESCRIPTION "A description of the media contained in this input sub-unit;This description is intended for display to a human operator.This description is not processed by the printer.  It is usedto provide information not expressible in terms of the othermedia attributes (e.g. prtInputMediaDimFeedDirChosen,prtInputMediaDimXFeedDirChosen, prtInputMediaWeight,prtInputMediaType). An example would be `legal tender bondpaper'. "
   USE "  "
   INTERACTION " "
   OPERATION ""
   ::= { prtInputEntry 12 }

-- 1.3.6.1.2.1.43.8.2.1.13
prtinputname  OBJECT-TYPE
   SYNTAX      binary (SIZE (0..63))
   ACCESS      read-write
   STATUS      optional
   DESCRIPTION "The name assigned to this input sub-unit. "
   USE "  "
   INTERACTION " "
   OPERATION ""
   ::= { prtInputEntry 13 }

-- 1.3.6.1.2.1.43.8.2.1.14
prtinputvendorname  OBJECT-TYPE
   SYNTAX      binary (SIZE (0..63))
   ACCESS      read-only
   STATUS      optional
   DESCRIPTION "The vendor name of this input sub-unit. "
   USE "  "
   INTERACTION " "
   OPERATION ""
   ::= { prtInputEntry 14 }

-- 1.3.6.1.2.1.43.8.2.1.15
prtinputmodel  OBJECT-TYPE
   SYNTAX      binary (SIZE (0..63))
   ACCESS      read-only
   STATUS      optional
   DESCRIPTION "The model name of this input sub-unit. "
   USE "  "
   INTERACTION " "
   OPERATION ""
   ::= { prtInputEntry 15 }

-- 1.3.6.1.2.1.43.8.2.1.16
prtinputversion  OBJECT-TYPE
   SYNTAX      binary (SIZE (0..63))
   ACCESS      read-only
   STATUS      optional
   DESCRIPTION "The version of this input sub-unit. "
   USE "  "
   INTERACTION " "
   OPERATION ""
   ::= { prtInputEntry 16 }

-- 1.3.6.1.2.1.43.8.2.1.17
prtinputserialnumber  OBJECT-TYPE
   SYNTAX      binary (SIZE (0..63))
   ACCESS      read-only
   STATUS      optional
   DESCRIPTION "The serial number assigned to this input sub-unit. "
   USE "  "
   INTERACTION " "
   OPERATION ""
   ::= { prtInputEntry 17 }

-- 1.3.6.1.2.1.43.8.2.1.18
prtinputdescription  OBJECT-TYPE
   SYNTAX      binary (SIZE (0..255))
   ACCESS      read-only
   STATUS      optional
   DESCRIPTION "A free-form text description of this inputsub-unit in the localization specified byprtGeneralCurrentLocalization. "
   USE "  "
   INTERACTION " "
   OPERATION ""
   ::= { prtInputEntry 18 }

-- 1.3.6.1.2.1.43.8.2.1.19
prtinputsecurity  OBJECT-TYPE
   SYNTAX      enumerated { ePother (1) , ePon (3) , ePoff (4) , ePnotPresent (5) }
   ACCESS      read-write
   STATUS      optional
   DESCRIPTION "Indicates if this input sub-unit has some securityassociated with it. "
   USE "  "
   INTERACTION " "
   OPERATION ""
   ::= { prtInputEntry 19 }

-- 1.3.6.1.2.1.43.8.2.1.2
prtinputtype  OBJECT-TYPE
   SYNTAX      enumerated { ePother (1) , ePunknown (2) , ePsheetFeedAutoRemovableTray (3) , ePsheetFeedAutoNonRemovableTray (4) , ePsheetFeedManual (5) , ePcontinuousRoll (6) , ePcontinuousFanFold (7) }
   ACCESS      read-only
   STATUS      optional
   DESCRIPTION "The type of technology (discriminated primarily according tofeeder mechanism type) employed by the input sub-unit.  Note,the Optional Input Class provides for a descriptor field tofurther qualify the other choice. "
   USE "  "
   INTERACTION " "
   OPERATION ""
   ::= { prtInputEntry 2 }

-- 1.3.6.1.2.1.43.8.2.1.24
prtinputmedialoadtimeout  OBJECT-TYPE
   SYNTAX      INTEGER
   ACCESS      read-write
   STATUS      optional
   DESCRIPTION "When the printer is not able to print due to a subunitbeing empty or the requested media must be manually loaded, theprinter will wait for the duration (in seconds) specified by thisobject. Upon expiration of the timeout, the printer will take theaction specified by prtInputNextIndex.The event which causes the printer to enter the waiting state isproduct specific. If the printer is not waiting for manually fedmedia, it may switch from an empty subunit to a different subunitwithout waiting for the timeout to expire.A value of (-1) implies 'other' or 'infinite' which translates to'wait forever'. The action which causes printing to continue isproduct specific. A value of (-2) implies 'unknown'. "
   USE "  "
   INTERACTION " "
   OPERATION ""
   ::= { printmib 9 }

-- 1.3.6.1.2.1.43.8.2.1.26
prtinputnextindex  OBJECT-TYPE
   SYNTAX      INTEGER
   ACCESS      read-write
   STATUS      optional
   DESCRIPTION "The value of prtInputIndex corresponding to the inputsubunit which will be used when this input subunit is emptied andthe timeout specified by prtInputMediaLoadTimeout expires. Avalue of zero(0) indicates that auto input switching will notoccur when this input subunit is emptied. If the timeoutspecified by prtInputLoadMediaTimeout expires and this value iszero(0), the job will be aborted. A value of (-1) means other.The value (-2) means 'unknown' and specifically indicates that animplementation specific method will determine the next inputsubunit to use at the time this subunit is emptied and thetimeout expires. The value(-3) means input switching is notsupported for this subunit. "
   USE "  "
   INTERACTION " "
   OPERATION ""
   ::= { printmib 9 }

-- 1.3.6.1.2.1.43.8.2.1.3
prtinputdimunit  OBJECT-TYPE
   SYNTAX      enumerated { ePtenThousandthsOfInches (3) , ePmicrometers (4) }
   ACCESS      read-only
   STATUS      optional
   DESCRIPTION "The unit of measurement for use calculating and relayingdimensional values for this input sub-unit. "
   USE "  "
   INTERACTION " "
   OPERATION ""
   ::= { prtInputEntry 3 }

-- 1.3.6.1.2.1.43.8.2.1.4
prtinputmediadimfeeddirdeclared  OBJECT-TYPE
   SYNTAX      INTEGER
   ACCESS      read-write
   STATUS      optional
   DESCRIPTION "This object provides the value of the declared dimension, inthe feed direction, of the media that is (or, if empty, was orwill be) in this input sub-unit.  The feed direction is thedirection in which the media is fed on this sub-unit.  Thisdimension is measured in input sub-unit dimensional units(prtInputDimUnit).  If this input sub-unit can reliably sensethis value, the value is sensed by the printer and may not bechanged by management requests.  Otherwise, the value may bechanged. The value (-1) means other and specifically meansthat this sub-unit places no restriction on this parameter.The value (-2) indicates unknown. "
   USE "  "
   INTERACTION " "
   OPERATION ""
   ::= { prtInputEntry 4 }

-- 1.3.6.1.2.1.43.8.2.1.5
prtinputmediadimxfeeddirdeclared  OBJECT-TYPE
   SYNTAX      INTEGER
   ACCESS      read-write
   STATUS      optional
   DESCRIPTION "This object provides the value of the declared dimension, inthe cross feed direction, of the media that is (or, if empty,was or will be) in this input sub-unit.  The cross  feeddirection is ninety degrees relative to the feed directionassociated with this sub-unit. This dimension is measured ininput sub-unit dimensional units (prtInputDimUnit).  If thisinput sub-unit can reliably sense this value, the value issensed by the printer and may not be changed by managementrequests. Otherwise, the value may be changed. The value (-1)means other and specifically means that this sub-unit placesno restriction on this parameter. The value (-2) indicatesunknown. "
   USE "  "
   INTERACTION " "
   OPERATION ""
   ::= { prtInputEntry 5 }

-- 1.3.6.1.2.1.43.8.2.1.6
prtinputmediadimfeeddirchosen  OBJECT-TYPE
   SYNTAX      INTEGER
   ACCESS      read-only
   STATUS      optional
   DESCRIPTION "The printer will act as if media of the chosen dimension (inthe feed direction) is present in this input source.  Notethat this value will be used even if the input tray is empty.Feed dimension measurements are taken relative to the feeddirection associated with that sub-unit and are in input sub-unitdimensional units (MediaUnit). If the printer supports thedeclared dimension, the granted dimension is the same asthe declared dimension. If not, the granted dimension isset to the closest dimension that the printer supportswhen the declared dimension is set. The value (-1) meansother and specifically indicates that this sub-unitplaces no restriction on this parameter. The value (-2)indicates unknown. "
   USE "  "
   INTERACTION " "
   OPERATION ""
   ::= { prtInputEntry 6 }

-- 1.3.6.1.2.1.43.8.2.1.7
prtinputmediadimxfeeddirchosen  OBJECT-TYPE
   SYNTAX      INTEGER
   ACCESS      read-only
   STATUS      optional
   DESCRIPTION "The printer will act as if media of the chosen dimension (inthe cross feed direction) is present in this input source.Note that this value will be used even if the input tray isempty.  The cross feed direction is ninety degrees relativeto the feed direction associated with this sub-unit. Thisdimension is measured in input sub-unit dimensional units(MediaUnit).  If the printer supports the declareddimension, the granted dimension is the same as thedeclared dimension. If not, the granted dimension is setto the closest dimension that the printer supports whenthe declared dimension is set. The value (-1) means otherand specifically indicates that this sub-unit places norestriction on this parameter.  The value (-2) indicatesunknown. "
   USE "  "
   INTERACTION " "
   OPERATION ""
   ::= { prtInputEntry 7 }

-- 1.3.6.1.2.1.43.8.2.1.8
prtinputcapacityunit  OBJECT-TYPE
   SYNTAX      enumerated { ePtenThousandthsOfInches (3) , ePmicrometers (4) , ePsheets (8) , ePfeet (16) , ePmeters (17) }
   ACCESS      read-only
   STATUS      optional
   DESCRIPTION "The unit of measurement for use in calculating and relayingcapacity values for this input sub-unit. "
   USE "  "
   INTERACTION " "
   OPERATION ""
   ::= { prtInputEntry 8 }

-- 1.3.6.1.2.1.43.8.2.1.9
prtinputmaxcapacity  OBJECT-TYPE
   SYNTAX      INTEGER
   ACCESS      read-write
   STATUS      optional
   DESCRIPTION "The maximum capacity of the input sub-unit in inputsub-unit capacity units (PrtCapacityUnitTC).  There is noconvention associated with the media itself so this valuereflects claimed capacity. If this input sub-unit canreliably sense this value, the value is sensed by theprinter and may not be changed by management requests;otherwise, the value may be written (by a RemoteControl Panel or a Management Application).The value (-1) means other and specificallyindicates that the sub-unit places no restrictionson this parameter.  The value (-2) means unknown. "
   USE "  "
   INTERACTION " "
   OPERATION ""
   ::= { prtInputEntry 9 }

-- 1.3.6.1.2.1.43.9.2.1.10
prtoutputversion  OBJECT-TYPE
   SYNTAX      binary (SIZE (0..63))
   ACCESS      read-only
   STATUS      optional
   DESCRIPTION "The version of this output sub-unit. "
   USE "  "
   INTERACTION " "
   OPERATION ""
   ::= { prtOutputEntry 10 }

-- 1.3.6.1.2.1.43.9.2.1.11
prtoutputserialnumber  OBJECT-TYPE
   SYNTAX      binary (SIZE (0..63))
   ACCESS      read-only
   STATUS      optional
   DESCRIPTION "The serial number assigned to this output sub-unit. "
   USE "  "
   INTERACTION " "
   OPERATION ""
   ::= { prtOutputEntry 11 }

-- 1.3.6.1.2.1.43.9.2.1.12
prtoutputdescription  OBJECT-TYPE
   SYNTAX      binary (SIZE (0..255))
   ACCESS      read-only
   STATUS      optional
   DESCRIPTION "  A free-form text description of this output sub-unit in thelocalization specified by prtGeneralCurrentLocalization. "
   USE "  "
   INTERACTION " "
   OPERATION ""
   ::= { prtOutputEntry 12 }

-- 1.3.6.1.2.1.43.9.2.1.13
prtoutputsecurity  OBJECT-TYPE
   SYNTAX      enumerated { ePother (1) , ePon (3) , ePoff (4) , ePnotPresent (5) }
   ACCESS      read-write
   STATUS      optional
   DESCRIPTION "Indicates if this output sub-unit has some security associatedwith it and if that security is enabled or not. "
   USE "  "
   INTERACTION " "
   OPERATION ""
   ::= { prtOutputEntry 13 }

-- 1.3.6.1.2.1.43.9.2.1.14
prtoutputdimunit  OBJECT-TYPE
   SYNTAX      enumerated { ePtenThousandthsOfInches (3) , ePmicrometers (4) }
   ACCESS      read-only
   STATUS      optional
   DESCRIPTION "The unit of measurement for use in calculating and relayingdimensional values for this output sub-unit. "
   USE "  "
   INTERACTION " "
   OPERATION ""
   ::= { prtOutputEntry 14 }

-- 1.3.6.1.2.1.43.9.2.1.15
prtoutputmaxdimfeeddir  OBJECT-TYPE
   SYNTAX      INTEGER
   ACCESS      read-write
   STATUS      optional
   DESCRIPTION "The maximum dimensions supported by this output sub-unitfor measurements taken parallel relative to the feeddirection associated with that sub-unit in outputsub-unit dimensional units (MediaUnit). If this outputsub-unit can reliably sense this value, the value issensed by the printer and may not be changed withmanagement protocol operations. "
   USE "  "
   INTERACTION " "
   OPERATION ""
   ::= { prtOutputEntry 15 }

-- 1.3.6.1.2.1.43.9.2.1.16
prtoutputmaxdimxfeeddir  OBJECT-TYPE
   SYNTAX      INTEGER
   ACCESS      read-write
   STATUS      optional
   DESCRIPTION "The maximum dimensions supported by this output sub-unitfor measurements taken ninety degrees relative to thefeed direction associated with that sub-unit in outputsub-unit dimensional units (MediaUnit). If this outputsub-unit can reliably sense this value, the value issensed by the printer and may not be changed withmanagement protocol operations. "
   USE "  "
   INTERACTION " "
   OPERATION ""
   ::= { prtOutputEntry 16 }

-- 1.3.6.1.2.1.43.9.2.1.17
prtoutputmindimfeeddir  OBJECT-TYPE
   SYNTAX      INTEGER
   ACCESS      read-write
   STATUS      optional
   DESCRIPTION "The minimum dimensions supported by this output sub-unitfor measurements taken parallel relative to the feeddirection associated with that sub-unit in outputsub-unit dimensional units (DimUnit).  If this outputsub-unit can reliably sense this value, the value issensed by the printer and may not be changed withmanagement protocol operations. "
   USE "  "
   INTERACTION " "
   OPERATION ""
   ::= { prtOutputEntry 17 }

-- 1.3.6.1.2.1.43.9.2.1.18
prtoutputmindimxfeeddir  OBJECT-TYPE
   SYNTAX      INTEGER
   ACCESS      read-write
   STATUS      optional
   DESCRIPTION "The minimum dimensions supported by this output sub-unitfor measurements taken ninety degrees relative to thefeed direction associated with that sub-unit in outputsub-unit dimensional units (DimUnit). If this outputsub-unit can reliably sense this value, the value issensed by the printer and may not be changed withmanagement protocol operations. "
   USE "  "
   INTERACTION " "
   OPERATION ""
   ::= { prtOutputEntry 18 }

-- 1.3.6.1.2.1.43.9.2.1.19
prtoutputstackingorder  OBJECT-TYPE
   SYNTAX      enumerated { ePunknown (2) , ePfirstToLast (3) , ePlastToFirst (4) }
   ACCESS      read-write
   STATUS      optional
   DESCRIPTION "The current state of the stacking order for theassociated output sub-unit. `FirstToLast' meansthat as pages are output the front of the next page isplaced against the back of the previous page.`LasttoFirst' means that as pages are output the backof the next page is placed against the front of theprevious page. "
   USE "  "
   INTERACTION " "
   OPERATION ""
   ::= { prtOutputEntry 19 }

-- 1.3.6.1.2.1.43.9.2.1.2
prtoutputtype  OBJECT-TYPE
   SYNTAX      enumerated { ePother (1) , ePunknown (2) , ePremovableBin (3) , ePunRemovableBin (4) , ePcontinuousRollDevice (5) , ePmailBox (6) , ePcontinousFanFold (7) }
   ACCESS      read-only
   STATUS      optional
   DESCRIPTION "The type of technology supported by this output sub-unit. "
   USE "  "
   INTERACTION " "
   OPERATION ""
   ::= { prtOutputEntry 2 }

-- 1.3.6.1.2.1.43.9.2.1.20
prtoutputpagedeliveryorientation  OBJECT-TYPE
   SYNTAX      enumerated { ePfaceUp (3) , ePfaceDown (4) }
   ACCESS      read-write
   STATUS      optional
   DESCRIPTION "The reading surface that will be `up' when pages aredelivered to the associated output sub-unit. Values arefaceUp and faceDown. (Note: interpretation of thesevalues is in general context-dependent based on locale;presentation of these values to an end-user should benormalized to the expectations of the user). "
   USE "  "
   INTERACTION " "
   OPERATION ""
   ::= { prtOutputEntry 20 }

-- 1.3.6.1.2.1.43.9.2.1.21
prtoutputbursting  OBJECT-TYPE
   SYNTAX      enumerated { ePother (1) , ePon (3) , ePoff (4) , ePnotPresent (5) }
   ACCESS      read-write
   STATUS      optional
   DESCRIPTION "This object indicates that the outputting sub-unitsupports bursting, and if so, whether the feature is enabled.Bursting is the process by which continuous media is separatedinto individual sheets, typically by bursting along pre-formedperforations. "
   USE "  "
   INTERACTION " "
   OPERATION ""
   ::= { prtOutputEntry 21 }

-- 1.3.6.1.2.1.43.9.2.1.22
prtoutputdecollating  OBJECT-TYPE
   SYNTAX      enumerated { ePother (1) , ePon (3) , ePoff (4) , ePnotPresent (5) }
   ACCESS      read-write
   STATUS      optional
   DESCRIPTION "This object indicates that the output supportssupports decollating, and if so, whether the featureis enabled. Decollating is the process by which theindividual parts within a multi-part form are separatedand sorted into separate stacks for each part. "
   USE "  "
   INTERACTION " "
   OPERATION ""
   ::= { prtOutputEntry 22 }

-- 1.3.6.1.2.1.43.9.2.1.23
prtoutputpagecollated  OBJECT-TYPE
   SYNTAX      enumerated { ePother (1) , ePon (3) , ePoff (4) , ePnotPresent (5) }
   ACCESS      read-write
   STATUS      optional
   DESCRIPTION "This object indicates that the output sub-unitsupports page collation, and if so, whether the feature isenabled. See glossary for definition of how this document definescollation. "
   USE "  "
   INTERACTION " "
   OPERATION ""
   ::= { prtOutputEntry 23 }

-- 1.3.6.1.2.1.43.9.2.1.24
prtoutputoffsetstacking  OBJECT-TYPE
   SYNTAX      enumerated { ePother (1) , ePon (3) , ePoff (4) , ePnotPresent (5) }
   ACCESS      read-write
   STATUS      optional
   DESCRIPTION "This object indicates that the output supportssupports offset stacking, and if so, whether the feature isenabled. See glossary for how Offset Stacking is defined by thisdocument. "
   USE "  "
   INTERACTION " "
   OPERATION ""
   ::= { prtOutputEntry 24 }

-- 1.3.6.1.2.1.43.9.2.1.3
prtoutputcapacityunit  OBJECT-TYPE
   SYNTAX      enumerated { ePtenThousandthsOfInches (3) , ePmicrometers (4) , ePsheets (8) , ePfeet (16) , ePmeters (17) }
   ACCESS      read-only
   STATUS      optional
   DESCRIPTION "The unit of measurement for use in calculating and relayingcapacity values for this output sub-unit."
   USE ""
   INTERACTION ""
   OPERATION ""
   ::= { prtOutputEntry 3 }

-- 1.3.6.1.2.1.43.9.2.1.4
prtoutputmaxcapacity  OBJECT-TYPE
   SYNTAX      INTEGER
   ACCESS      read-write
   STATUS      optional
   DESCRIPTION "The maximum capacity of this output sub-unit in outputsub-unit capacity units (PrtCapacityUnitTC). There is noconvention associated with the media itself so this valueessentially reflects claimed capacity. If this outputsub-unit can reliably sense this value, the value issensed by the printer and may not be changed by managementrequests; otherwise, the value may be written(by a Remote Control Panel or a Management Application).The value (-1) means other and specifically indicatesthat the sub-unit places no restrictions on this parameter.The value (-2) means unknown. "
   USE "  "
   INTERACTION " "
   OPERATION ""
   ::= { prtOutputEntry 4 }

-- 1.3.6.1.2.1.43.9.2.1.5
prtoutputremainingcapacity  OBJECT-TYPE
   SYNTAX      INTEGER
   ACCESS      read-write
   STATUS      optional
   DESCRIPTION "The remaining capacity of the possible output sub-unitcapacity in output sub-unit capacity units (PrtCapacityUnitTC)of this output sub-unit. If this output sub-unit canreliably sense this value, the value is sensed by theprinter and may not be modified by management requests;otherwise, the value may be written (bya Remote Control Panel or a ManagementApplication).  The value (-1) means other andspecifically indicates that the sub-unit places norestrictions on this parameter.  The value (-2) meansunknown.  The value (-3) means that the printer knows thatthere remains capacity for at least one unit. "
   USE "  "
   INTERACTION " "
   OPERATION ""
   ::= { prtOutputEntry 5 }

-- 1.3.6.1.2.1.43.9.2.1.6
prtoutputstatus  OBJECT-TYPE
   SYNTAX      INTEGER
   ACCESS      read-only
   STATUS      optional
   DESCRIPTION "The current status of this output sub-unit. "
   USE "  "
   INTERACTION " "
   OPERATION ""
   ::= { prtOutputEntry 6 }

-- 1.3.6.1.2.1.43.9.2.1.7
prtoutputname  OBJECT-TYPE
   SYNTAX      binary (SIZE (0..63))
   ACCESS      read-write
   STATUS      optional
   DESCRIPTION "The name assigned to this output sub-unit. "
   USE "  "
   INTERACTION " "
   OPERATION ""
   ::= { prtOutputEntry 7 }

-- 1.3.6.1.2.1.43.9.2.1.8
prtoutputvendorname  OBJECT-TYPE
   SYNTAX      binary (SIZE (0..63))
   ACCESS      read-only
   STATUS      optional
   DESCRIPTION "The vendor name of this output sub-unit. "
   USE "  "
   INTERACTION " "
   OPERATION ""
   ::= { prtOutputEntry 8 }

-- 1.3.6.1.2.1.43.9.2.1.9
prtoutputmodel  OBJECT-TYPE
   SYNTAX      binary (SIZE (0..63))
   ACCESS      read-only
   STATUS      optional
   DESCRIPTION "The name assigned to this output sub-unit. "
   USE "  "
   INTERACTION " "
   OPERATION ""
   ::= { prtOutputEntry 9 }


END
