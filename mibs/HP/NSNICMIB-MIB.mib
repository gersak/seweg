-- ****************************************************************************
-- HP NSA NIC MIB
-- October 24, 1997
--
-- Copyright Hewlett-Packard Company 1994-97.
-- All rights reserved.
--
-- The information in this document is subject to change without notice.
--
-- The HP enterprise number is 11. The ASN.1 prefix to, and including,
-- the HP enterprise ID is 1.3.6.1.4.1.11.
--
-- ****************************************************************************
-- Summary of HP NSA NIC MIB
-- ****************************************************************************
-- hp                                              (1.3.6.1.4.1.11)
--    nm                                           (hp.2)
--       hpnsa                                     (nm.23)
--          nicObject Group                        (hpnsa.18)
--             nicDrvConfig Group                  (hpnsa.18.1)
--                nicDrvConfigTable                (hpnsa.18.1.1)
--                   nicDrvConfigEntry             (hpnsa.18.1.1.1)
--                      nicDrvConfigIndex          (hpnsa.18.1.1.1.1)
--                      nicDrvcfgName              (hpnsa.18.1.1.1.2)
--                      nicDrvcfgDescript          (hpnsa.18.1.1.1.3)
--                      nicDrvcfgType              (hpnsa.18.1.1.1.4)
--                      nicDrvcfgPhyAddr           (hpnsa.18.1.1.1.5)
--                      nicDrvcfgMajor             (hpnsa.18.1.1.1.6)
--                      nicDrvcfgMinor             (hpnsa.18.1.1.1.7)
--                      nicDrvcfgSlot              (hpnsa.18.1.1.1.8)
--                      nicDrvcfgIOport0           (hpnsa.18.1.1.1.9)
--                      nicDrvcfgIOport1           (hpnsa.18.1.1.1.10)
--                      nicDrvcfgInterrupt0        (hpnsa.18.1.1.1.11)
--                      nicDrvcfgInterrupt1        (hpnsa.18.1.1.1.12)
--                      nicDrvcfgDMA0              (hpnsa.18.1.1.1.13)
--                      nicDrvcfgDMA1              (hpnsa.18.1.1.1.14)
--                      nicDrvcfgMemory0           (hpnsa.18.1.1.1.15)
--                      nicDrvcfgMemory1           (hpnsa.18.1.1.1.16)
--                      nicDrvcfgMulticast         (hpnsa.18.1.1.1.17)
--                      nicDrvcfgPromiscuous       (hpnsa.18.1.1.1.18)
--                      nicDrvcfgMaxiumumSize      (hpnsa.18.1.1.1.19)
--                      nicDrvcfgSpeed             (hpnsa.18.1.1.1.20)
--                      nicDrvcfgTransportTime     (hpnsa.18.1.1.1.21)
--                      nicDrvcfgSendRetries       (hpnsa.18.1.1.1.22)
--                      nicDrvcfgMode              (hpnsa.18.1.1.1.23)
--                      nicDrvcfgNumFrames         (hpnsa.18.1.1.1.24)                   
--                      nicDrvcfgAftGroupId        (hpnsa.18.1.1.1.25)
--                      nicDrvcfgAftBusNo          (hpnsa.18.1.1.1.26)
--                      nicDrvcfgAftBusDeviceId    (hpnsa.18.1.1.1.27)
--                      nicDrvcfgAftPciVendorId    (hpnsa.18.1.1.1.28)
--                      nicDrvcfgAftPciDeviceId    (hpnsa.18.1.1.1.29)
--                      nicDrvcfgAftPciSubSysVendorId   (hpnsa.18.1.1.1.30)
--                      nicDrvcfgAftPciSubSysDeviceId (hpnsa.18.1.1.1.31)
--                      nicDrvcfgAftStatus          (hpnsa.18.1.1.1.32)
--                      nicDrvcfgAftMode            (hpnsa.18.1.1.1.33)



--             nicStatistics Group                 (hpnsa.18.2)
--                nicStatisticsTable               (hpnsa.18.2.1)
--                   nicStatisticsEntry            (hpnsa.18.2.1.1)
--                      nicStatisticsIndex         (hpnsa.18.2.1.1.1)
--                      nicTtlTxPacket             (hpnsa.18.2.1.1.2)
--                      nicDeltaTtlTxPacket        (hpnsa.18.2.1.1.3)
--                      nicTtlRxPacket             (hpnsa.18.2.1.1.4)
--                      nicDeltaTtlRxPacket        (hpnsa.18.2.1.1.5)
--                      nicGetECBFails             (hpnsa.18.2.1.1.6)
--                      nicTxTooBig                (hpnsa.18.2.1.1.7)
--                      nicRxTooBig                (hpnsa.18.2.1.1.8)
--                      nicRxOverflow              (hpnsa.18.2.1.1.9)
--                      nicTxMisc                  (hpnsa.18.2.1.1.10)
--                      nicRxMisc                  (hpnsa.18.2.1.1.11)
--                      nicRxCRC                   (hpnsa.18.2.1.1.12)
--                      nicTxOKByte                (hpnsa.18.2.1.1.13)
--                      nicDeltaTxOKByte           (hpnsa.18.2.1.1.14)
--                      nicRxOKByte                (hpnsa.18.2.1.1.15)
--                      nicDeltaRxOKByte           (hpnsa.18.2.1.1.16)
--                      nicTxGroup                 (hpnsa.18.2.1.1.17)
--                      nicDeltaTxGroup            (hpnsa.18.2.1.1.18)
--                      nicRxGroup                 (hpnsa.18.2.1.1.19)
--                      nicDeltaRxGroup            (hpnsa.18.2.1.1.20)
--                      nicAdapterReset            (hpnsa.18.2.1.1.21)
--                      nicQDepth                  (hpnsa.18.2.1.1.22)
--                      nicRcvByffers              (hpnsa.18.2.1.1.23)
--                      nicRcvBuffers75Pct         (hpnsa.18.2.1.1.24)
--                      nicRcvBuffersCkOut         (hpnsa.18.2.1.1.25)
--                      nicRcvBuffersMaxSize       (hpnsa.18.2.1.1.26)
--                      nicNumCustCounter          (hpnsa.18.2.1.1.27)
--             nicCustomStats Group                (hpnsa.18.3)
--                nicCustStatTable                 (hpnsa.18.3.1)
--                   nicCustEntry                  (hpnsa.18.3.1.1)
--                      nicCustIndex               (hpnsa.18.3.1.1.1) 
--                      nicIndex                   (hpnsa.18.3.1.1.2)
--                      nicCustCounter             (hpnsa.18.3.1.1.3)
--                      nicCustCounterString       (hpnsa.18.3.1.1.4)
--             nicErrors Group                     (hpnsa.18.4)
--                nicErrorsTable                   (hpnsa.18.4.1)
--                   nicErrorsEntry                (hpnsa.18.4.1.1)
--                      nicErrorsIndex             (hpnsa.18.4.1.1.1)
--                      nicTxOKSingleCollision     (hpnsa.18.4.1.1.2)
--                      nicTxOMultipleCollision    (hpnsa.18.4.1.1.3)
--                      nicTxOKDeferred            (hpnsa.18.4.1.1.4)        
--                      nicTxAbortLateCollision    (hpnsa.18.4.1.1.5)
--                      nicTxAbortExcessCollision  (hpnsa.18.4.1.1.6)
--                      nicTxAbortCarrierSense     (hpnsa.18.4.1.1.7)
--                      nicTxAbortExcessiveDeferral(hpnsa.18.4.1.1.8)
--                      nicRxAbortFrameAlignment   (hpnsa.18.4.1.1.9)
--                      nicHWRxMismatch            (hpnsa.18.4.1.1.10)
--                      nicTtlTxErrPacket          (hpnsa.18.4.1.1.11)
--                      nicTtlRxErrPacket          (hpnsa.18.4.1.1.12)            
--             nicMiscellaneous Group              (hpnsa.18.5)
--                nicNumBoards                     (hpnsa.18.5.1)
--                nicAdapterType                   (hpnsa.18.5.2)
--             nicFrameType Group                  (hpnsa.18.6)
--                nicFrameTypeTable                (hpnsa.18.6.1)
--                   nicFrameTypeEntry             (hpnsa.18.6.1.1)
--                      nicFrameTypeIndex          (hpnsa.18.6.1.1.1)
--                      nicCardIndex               (hpnsa.18.6.1.1.2)
--                      nicFrameTypeString         (hpnsa.18.6.1.1.3)   
--             nicParms Group                      (hpnsa.18.7)
--                nicCommonParms Group             (hpnsa.18.7.1)
--                   nicParmSampling               (hpnsa.18.7.1.1)
--                   nicParmProcessing             (hpnsa.18.7.1.2)
--                   nicParmRxErrCount             (hpnsa.18.7.1.3)
--                   nicParmRxErrDelta             (hpnsa.18.7.1.4)
--                   nicParmRxErrPct               (hpnsa.18.7.1.5)
--                   nicParmTxErrCount             (hpnsa.18.7.1.6)
--                   nicParmTxErrDelta             (hpnsa.18.7.1.7)
--                   nicParmTxErrPct               (hpnsa.18.7.1.8)
--                   nicParmAdapterResetCount      (hpnsa.18.7.1.9)
--                   nicParmAdapterResetDelta      (hpnsa.18.7.1.10)
--                   nicParmAdapterResetPct        (hpnsa.18.7.1.11)
--                   nicParmAlignmentCount         (hpnsa.18.7.1.12)
--                   nicParmAlignmentDelta         (hpnsa.18.7.1.13)
--                   nicParmAlignmentPct           (hpnsa.18.7.1.14)
--                   nicParmFrameTooLongCount      (hpnsa.18.7.1.15)
--                   nicParmFrameTooLongDelta      (hpnsa.18.7.1.16)
--                   nicParmFrameTooLongPct        (hpnsa.18.7.1.17)
--                   nicParmHardwareMismatchCount  (hpnsa.18.7.1.18)
--                   nicParmHardwareMismathDelta   (hpnsa.18.7.1.19)
--                   nicParmHardwareMismatchPct    (hpnsa.18.7.1.20)
--                   nicParmLateCollisionCount     (hpnsa.18.7.1.21)
--                   nicParmLateCollisionDelta     (hpnsa.18.7.1.22)
--                   nicParmLateCollisionPct       (hpnsa.18.7.1.23)
--                   nicParmExcessCollisionCount   (hpnsa.18.7.1.24)
--                   nicParmExcessCollisionDelta   (hpnsa.18.7.1.25)
--                   nicParmExcessCollisionPct     (hpnsa.18.7.1.26)
--                   nicParmCarrierSenseCount      (hpnsa.18.7.1.27)
--                   nicParmCarrierSenseDelta      (hpnsa.18.7.1.28)
--                   nicParmCarrierSensePct        (hpnsa.18.7.1.29)
--                   nicParmDeferralCount          (hpnsa.18.7.1.30)
--                   nicParmDeferralDelta          (hpnsa.18.7.1.31)
--                   nicParmDeferralPct            (hpnsa.18.7.1.32)
--                   nicParmNoECBCount             (hpnsa.18.7.1.33)
--                   nicParmNoECBDelta             (hpnsa.18.7.1.34)
--                   nicParmNoECBPct               (hpnsa.18.7.1.35)
--                   nicParmRxOverflowCount        (hpnsa.18.7.1.36)
--                   nicParmRxOverflowDelta        (hpnsa.18.7.1.37)
--                   nicParmRxOverflowPct          (hpnsa.18.7.1.38)
--                   nicParmUtilizationCount       (hpnsa.18.7.1.39)
--                   nicParmAdapterType            (hpnsa.18.7.1.40) 
--                   nicParmLineErrCount           (hpnsa.18.7.1.41)    *
--                   nicParmLineErrDelta           (hpnsa.18.7.1.42)    *
--                   nicParmLineErrPct             (hpnsa.18.7.1.43)    *
--                   nicParmLostFramesCount        (hpnsa.18.7.1.44)    *
--                   nicParmLostFramesDelta        (hpnsa.18.7.1.45)    *
--                   nicParmLostFramesPct          (hpnsa.18.7.1.46)    *
--                   nicParmBurstErrCount          (hpnsa.18.7.1.47)    *
--                   nicParmBurstErrDelta          (hpnsa.18.7.1.48)    *
--                   nicParmBurstErrPct            (hpnsa.18.7.1.49)    *
--                   nicParmACErrCount             (hpnsa.18.7.1.50)    *
--                   nicParmACErrDelta             (hpnsa.18.7.1.51)    *
--                   nicParmACErrPct               (hpnsa.18.7.1.52)    *
--                   nicParmAbortDelimitersCount   (hpnsa.18.7.1.53)    *
--                   nicParmAbortDelimitersDelta   (hpnsa.18.7.1.54)    *
--                   nicParmAbortDelimitersPct     (hpnsa.18.7.1.55)    *
--                   nicParmFrameCopiedErrCount    (hpnsa.18.7.1.56)    *
--                   nicParmFrameCopiedErrDelta    (hpnsa.18.7.1.57)    *
--                   nicParmFrameCopiedErrPct      (hpnsa.18.7.1.58)    *
--                   nicParmFrequencyErrCount      (hpnsa.18.7.1.59)    *
--                   nicParmFrequencyErrDelta      (hpnsa.18.7.1.60)    *
--                   nicParmFrequencyErrPct        (hpnsa.18.7.1.61)    *
--                   nicParmTokenErrCount          (hpnsa.18.7.1.62)    *
--                   nicParmTokenErrDelta          (hpnsa.18.7.1.63)    *
--                   nicParmTokenErrPct            (hpnsa.18.7.1.64)    *
--                   nicParmInternalErrCount       (hpnsa.18.7.1.65)    *
--                   nicParmInternalErrDelta       (hpnsa.18.7.1.66)    *
--                   nicParmInternalErrPct         (hpnsa.18.7.1.67)    *
--                   nicParmAftFailOverErrCount    (hpnsa.18.7.1.68)    *
--                   nicParmAftFailOverErrDelta    (hpnsa.18.7.1.69)    *
--                   nicParmAftRecoveryErrCount    (hpnsa.18.7.1.70)    *
--                   nicParmAftRecoveryErrDelta    (hpnsa.18.7.1.71)    *
--                   nicParmAftStandbyErrCount     (hpnsa.18.7.1.72)    *
--                   nicParmAftStandbyErrDelta     (hpnsa.18.7.1.73)    *
--                   nicParmAftGroupFailErrCount   (hpnsa.18.7.1.74)    *
--                   nicParmAftGroupFailErrDelta   (hpnsa.18.7.1.75)    *
--                nicStarfighterParms Group        (hpnsa.18.7.2)
--                nicTwisterParms Group            (hpnsa.18.7.3)
--                nicMasterParms Group             (hpnsa.18.7.4)
--                nicShastaParms Group             (hpnsa.18.7.5)
--             nicTokenRingStatisticsGroup         (hpnsa.18.8)         *
--                nicTokenRingStatisticsTable      (hpnsa.18.8.1)       *
--                   nicTokenRingStatisticsEntry   (hpnsa.18.8.1.1)     *
--                      nicTokenRingStatisticsIndex(hpnsa.18.8.1.1.1)   *
--                      nicFunctionalAddress       (hpnsa.18.8.1.1.2)   *
--                      nicGroupAddress            (hpnsa.18.8.1.1.3)   *
--                      nicLastOpenStatus          (hpnsa.18.8.1.1.4)   *
--                      nicRingStatus              (hpnsa.18.8.1.1.5)   *
--                      nicRingState               (hpnsa.18.8.1.1.6)   *
--             nicTokenRingErrors Group            (hpnsa.18.9)         *
--                nicTokenRingErrorsTable          (hpnsa.18.9.1)       *
--                   nicTokenRingErrorsEntry       (hpnsa.18.9.1.1)     *
--                      nicTokenRingErrorsIndex    (hpnsa.18.9.1.1.1)   *
--                      nicLineErrors              (hpnsa.18.9.1.1.2)   *
--                      nicLostFrames              (hpnsa.18.9.1.1.3)   *
--                      nicBurstErrors             (hpnsa.18.9.1.1.4)   *
--                      nicACErrors                (hpnsa.18.9.1.1.5)   *
--                      nicAbortDelimiters         (hpnsa.18.9.1.1.6)   *
--                      nicFrameCopiedErrors       (hpnsa.18.9.1.1.7)   *
--                      nicFrequencyErrors         (hpnsa.18.9.1.1.8)   *
--                      nicTokenErrors             (hpnsa.18.9.1.1.9)   *
--                      nicInternalErrors          (hpnsa.18.9.1.1.10)  *
--
-- ****************************************************************************

NSNICMIB-MIB DEFINITIONS ::= BEGIN

	IMPORTS
	   Counter, enterprises
	      FROM RFC1155-SMI
	   OBJECT-TYPE
	      FROM SNMPv2-SMI
	   DisplayString, PhysAddress
	       FROM RFC1213-MIB;
	
	hp                      OBJECT IDENTIFIER ::= {enterprises 11}
	nm                      OBJECT IDENTIFIER ::= {hp 2}
	hpnsa                   OBJECT IDENTIFIER ::= {nm 23}
	
	nicObject               OBJECT IDENTIFIER ::= {hpnsa 18} 
	
	nicDrvConfig            OBJECT IDENTIFIER ::= {nicObject 1}
	nicStatistics           OBJECT IDENTIFIER ::= {nicObject 2}
	nicCustomStats          OBJECT IDENTIFIER ::= {nicObject 3}
	nicErrors               OBJECT IDENTIFIER ::= {nicObject 4} 
	nicMiscellaneous        OBJECT IDENTIFIER ::= {nicObject 5}  
	nicFrameType            OBJECT IDENTIFIER ::= {nicObject 6}
	nicParms                OBJECT IDENTIFIER ::= {nicObject 7}
	nicTokenRingStatistics  OBJECT IDENTIFIER ::= {nicObject 8}
	nicTokenRingErrors      OBJECT IDENTIFIER ::= {nicObject 9}

	nicCommonParms          OBJECT IDENTIFIER ::= {nicParms 1}
	nicStarfighterParms     OBJECT IDENTIFIER ::= {nicParms 2}
	nicTwisterParms         OBJECT IDENTIFIER ::= {nicParms 3}
	nicMasterParms          OBJECT IDENTIFIER ::= {nicParms 4}
	nicShastaParms          OBJECT IDENTIFIER ::= {nicParms 5}

	-- the NIC Driver Configuration Table
    
    nicDrvConfigTable           OBJECT-TYPE
       SYNTAX                           SEQUENCE OF NicDrvConfigEntry
       ACCESS                           not-accessible
       STATUS                           mandatory
       DESCRIPTION
	"A list of Driver Configuration Information"
       ::= {nicDrvConfig 1}
       
    nicDrvConfigEntry           OBJECT-TYPE
       SYNTAX                           NicDrvConfigEntry
       ACCESS                           not-accessible
       STATUS                           mandatory
       DESCRIPTION
	"Driver Configuration Information Table Entry."
       INDEX                            { nicDrvConfigIndex }
       ::= { nicDrvConfigTable 1 }
       
    NicDrvConfigEntry           ::= SEQUENCE {
						nicDrvConfigIndex
								INTEGER,
						nicDrvcfgName
								DisplayString,
						nicDrvcfgDescript
								DisplayString,
						nicDrvcfgType
								Integer,
						nicDrvcfgPhyAddr
								PhysAddress,
						nicDrvcfgMajor
								INTEGER,
						nicDrvcfgMinor
								INTEGER,
						nicDrvcfgSlot
								INTEGER,
						nicDrvcfgIOport0
								OCTET STRING,
						nicDrvcfgIOport1
								OCTET STRING,
						nicDrvcfgInterrupt0
								INTEGER,
						nicDrvcfgInterrupt1
								INTEGER,
						nicDrvcfgDMA0
								INTEGER,
						nicDrvcfgDMA1
								INTEGER,
						nicDrvcfgMemory0
								OCTET STRING,
						nicDrvcfgMemory1
								OCTET STRING,
						nicDrvcfgMulticast
								INTEGER,
						nicDrvcfgPromiscuous
								INTEGER,
						nicDrvcfgMaximumSize 
								INTEGER,
						nicDrvcfgSpeed
								INTEGER,
						nicDrvcfgTransportTime
								INTEGER,
						nicDrvcfgSendRetries
								INTEGER,
						nicDrvcfgMode
								INTEGER,
						nicDrvcfgNumFrames
								INTEGER,                                 
						nicDrvcfgAftGroupId
								INTEGER,
                      				nicDrvcfgAftBusNo               
								OCTET STRING,
                      				nicDrvcfgAftBusDeviceId        
								OCTET STRING,

                      				nicDrvcfgAftPciVendorId          
								OCTET STRING,

                      				nicDrvcfgAftPciDeviceId         
								OCTET STRING,

                      				nicDrvcfgAftPciSubSysVendorId   
								OCTET STRING,

                      				nicDrvcfgAftPciSubSysDeviceId 
								OCTET STRING,

                      				nicDrvcfgAftStatus              
								INTEGER,                                 
                      				nicDrvcfgAftMode                
								INTEGER                                 
						
						}
						
						
    nicDrvConfigIndex           OBJECT-TYPE
	SYNTAX                          INTEGER
	ACCESS                          read-only
	STATUS                          mandatory
	DESCRIPTION
	  "Index into Driver Configuration Information Table."
	::= { nicDrvConfigEntry 1 }
						
	nicDrvcfgName   OBJECT-TYPE
	   SYNTAX       DisplayString (SIZE (0..255))
	   ACCESS       read-only
	   STATUS       mandatory
	   DESCRIPTION  
		"Driver Name. Never Changes"
	   ::= {nicDrvConfigEntry 2}
	
	nicDrvcfgDescript       OBJECT-TYPE
	   SYNTAX               DisplayString (SIZE (0..255))
	   ACCESS               read-only
	   STATUS               mandatory
	   DESCRIPTION
		"Driver description, does not change"
	   ::= {nicDrvConfigEntry 3}
	
	nicDrvcfgType   OBJECT-TYPE
	   SYNTAX       INTEGER 
	   { Unknown(0),
	     HP-Starfighter(1),
	     HP-Twister(2),
	     HP-Busmaster(3),
	     HP-Shasta(4)}
	   ACCESS       read-only
	   STATUS       mandatory
	   DESCRIPTION
		"Type of NIC"
	   ::= {nicDrvConfigEntry 4}

	nicDrvcfgPhyAddr        OBJECT-TYPE
	   SYNTAX               PhysAddress (SIZE (0..80))
	   ACCESS               read-only
	   STATUS               mandatory
	   DESCRIPTION
		"Address at the protocol layer immediately below
		 the network layer"
	   ::= {nicDrvConfigEntry 5}

	nicDrvcfgMajor  OBJECT-TYPE
	   SYNTAX       INTEGER (0..65535)
	   ACCESS       read-only
	   STATUS       mandatory
	   DESCRIPTION
		"The major revision level of the driver"
	   ::= {nicDrvConfigEntry 6}

	nicDrvcfgMinor  OBJECT-TYPE
	   SYNTAX       INTEGER (0..65535)
	   ACCESS       read-only
	   STATUS       mandatory
	   DESCRIPTION
		"The minor revision level of the driver"
	   ::= {nicDrvConfigEntry 7}

	nicDrvcfgSlot   OBJECT-TYPE
	   SYNTAX       INTEGER (0..16)
	   ACCESS       read-only
	   STATUS       mandatory
	   DESCRIPTION
		"Slot where the board is installed (EISA only)"
	   ::= {nicDrvConfigEntry 8}

	nicDrvcfgIOport0 OBJECT-TYPE
	   SYNTAX        OCTET STRING (SIZE (6))
	   ACCESS        read-only
	   STATUS        mandatory
	   DESCRIPTION
		"Primary Base IO port"
	   ::= {nicDrvConfigEntry 9}
	
	nicDrvcfgIOport1 OBJECT-TYPE
	   SYNTAX        OCTET STRING (SIZE (6))
	   ACCESS        read-only
	   STATUS        mandatory
	   DESCRIPTION
		"Secondary Base IO port"
	   ::= {nicDrvConfigEntry 10}

	nicDrvcfgInterrupt0    OBJECT-TYPE
	   SYNTAX              INTEGER {Unused(255)}
	   ACCESS              read-only
	   STATUS              mandatory
	   DESCRIPTION
		"The Primary IRQ number/interrupt vector"
	   ::= {nicDrvConfigEntry 11}
	
	nicDrvcfgInterrupt1    OBJECT-TYPE
	   SYNTAX              INTEGER {Unused(255)}
	   ACCESS              read-only
	   STATUS              mandatory
	   DESCRIPTION
		"The Secondary IRQ number/interrupt vector"
	   ::= {nicDrvConfigEntry 12}

	nicDrvcfgDMA0            OBJECT-TYPE
	   SYNTAX               INTEGER {Unused(255)}
	   ACCESS               read-only
	   STATUS               mandatory
	   DESCRIPTION
		"The Primary DMA channel if applicable"
	   ::= {nicDrvConfigEntry 13}
	
	nicDrvcfgDMA1            OBJECT-TYPE
	   SYNTAX               INTEGER {Unused(255)}
	   ACCESS               read-only
	   STATUS               mandatory
	   DESCRIPTION
		"The Secondary DMA channel if applicable"
	   ::= {nicDrvConfigEntry 14}

	nicDrvcfgMemory0        OBJECT-TYPE
	   SYNTAX               OCTET STRING (SIZE (6))
	   ACCESS               read-only
	   STATUS               mandatory
	   DESCRIPTION
		"Memory Mapped Address 0 if applicable"
	   ::= {nicDrvConfigEntry 15}

	nicDrvcfgMemory1        OBJECT-TYPE
	   SYNTAX               OCTET STRING (SIZE (6))
	   ACCESS               read-only
	   STATUS               mandatory
	   DESCRIPTION
		"Memory Mapped Address 1 if applicable"
	   ::= {nicDrvConfigEntry 16}

	nicDrvcfgMulticast      OBJECT-TYPE
	   SYNTAX               INTEGER (0..1)
	   ACCESS               read-only
	   STATUS               mandatory
	   DESCRIPTION
		"Whether driver supports multicast addressing"
	   ::= {nicDrvConfigEntry 17}

	nicDrvcfgPromiscuous      OBJECT-TYPE
	   SYNTAX                 INTEGER (0..1)
	   ACCESS                 read-only
	   STATUS                 mandatory
	   DESCRIPTION
		"Whether driver is in promiscuous mode"
	   ::= {nicDrvConfigEntry 18}  
	   
	nicDrvcfgMaximumSize      OBJECT-TYPE
	   SYNTAX                 INTEGER 
	   ACCESS                 read-only
	   STATUS                 mandatory
	   DESCRIPTION
		"This is the ECB's maximum buffer size"
	   ::= {nicDrvConfigEntry 19}
	   
	nicDrvcfgSpeed      OBJECT-TYPE
	   SYNTAX                 INTEGER 
	   ACCESS                 read-only
	   STATUS                 mandatory
	   DESCRIPTION
		"Driver transmission speed in Mbits"
	   ::= {nicDrvConfigEntry 20}
	   
	   
	nicDrvcfgTransportTime    OBJECT-TYPE
	   SYNTAX                 INTEGER 
	   ACCESS                 read-only
	   STATUS                 mandatory
	   DESCRIPTION
		"Time(in ticks) to transmit a 576-byte packet"
	   ::= {nicDrvConfigEntry 21}
	   
	nicDrvcfgSendRetries      OBJECT-TYPE
	   SYNTAX                 INTEGER 
	   ACCESS                 read-only
	   STATUS                 mandatory
	   DESCRIPTION
		"Number of retries for transmission before abort"
	   ::= {nicDrvConfigEntry 22}      
    
    nicDrvcfgMode                     OBJECT-TYPE
	   SYNTAX                 INTEGER
	   { non-100VG(0), 
	     100VG(1)}
	   ACCESS                 read-only
	   STATUS                 mandatory
	   DESCRIPTION
		"Mode of transmission, 100VG enabled or disabled"
	   ::= {nicDrvConfigEntry 23}      

    nicDrvcfgBindFrames       OBJECT-TYPE
	   SYNTAX                 INTEGER 
	   ACCESS                 read-only
	   STATUS                 mandatory
	   DESCRIPTION
		"Number of Frames types bound to this Driver"
	   ::= {nicDrvConfigEntry 24}      


	-- the NIC AFT Driver Information  
	-- sms 11/18/97

    nicDrvcfgAftGroupId       	OBJECT-TYPE
	   SYNTAX                 INTEGER (0..7)
	   ACCESS                 read-only
	   STATUS                 mandatory
	   DESCRIPTION
		"Adavanced Fault Tolerance(AFT) Group Id bound to this Adapter"
	   ::= {nicDrvConfigEntry 25}      


    nicDrvcfgAftBusNo  		OBJECT-TYPE
	   SYNTAX        OCTET STRING (SIZE (1))
	   ACCESS                 read-only
	   STATUS                 mandatory
	   DESCRIPTION
		"PCI Bus Number bound to this Adapter"
	   ::= {nicDrvConfigEntry 26}      

    nicDrvcfgAftBusDeviceId    	OBJECT-TYPE
	   SYNTAX        OCTET STRING (SIZE (1))
	   ACCESS                 read-only
	   STATUS                 mandatory
	   DESCRIPTION
		"PCI Bus Device Id bound to this Adapter"
	   ::= {nicDrvConfigEntry 27}      

    nicDrvcfgAftPciVenodrId    	OBJECT-TYPE
	   SYNTAX        OCTET STRING (SIZE (2))
	   ACCESS                 read-only
	   STATUS                 mandatory
	   DESCRIPTION
		"PCI Vendor Id bound to this Adapter"
	   ::= {nicDrvConfigEntry 28}      

    nicDrvcfgAftPciDeviceId    	OBJECT-TYPE
	   SYNTAX        OCTET STRING (SIZE (2))
	   ACCESS                 read-only
	   STATUS                 mandatory
	   DESCRIPTION
		"PCI Device Id bound to this Driver"
	   ::= {nicDrvConfigEntry 29}

    nicDrvcfgAftPciSubSysVendorId    	OBJECT-TYPE
	   SYNTAX        OCTET STRING (SIZE (2))
	   ACCESS                 read-only
	   STATUS                 mandatory
	   DESCRIPTION
		"PCI Subsystem Vendor Id bound to this Adapter"
	   ::= {nicDrvConfigEntry 30}


    nicDrvcfgAftPciSubSysDeviceId    	OBJECT-TYPE
	   SYNTAX        OCTET STRING (SIZE (2))
	   ACCESS                 read-only
	   STATUS                 mandatory
	   DESCRIPTION
		"PCI Subsystem Device Id bound to this Adapter"
	   ::= {nicDrvConfigEntry 31}

    nicDrvcfgAftStatus        OBJECT-TYPE
	   SYNTAX                 INTEGER 
	   { Standby(0), 
	     Active(1),
	     Failed(2)}
	   ACCESS                 read-only
	   STATUS                 mandatory
	   DESCRIPTION
		"Adavanced Fault Tolerance(AFT) Status(Standby, Active or Failed) bound to this Adapter"
	   ::= {nicDrvConfigEntry 32}      

    nicDrvcfgAftMode          OBJECT-TYPE
	   SYNTAX                 INTEGER 
	   { Secondary(0), 
	     Primary(1)}
	   ACCESS                 read-only
	   STATUS                 mandatory
	   DESCRIPTION
		"Adavanced Fault Tolerance(AFT) Mode (Primary or Secondary) bound this Adapter"
	   ::= {nicDrvConfigEntry 33}      


	-- the NIC Driver Statistic Table 
	
	nicStatisticsTable              OBJECT-TYPE
	   SYNTAX                               SEQUENCE OF NicStatisticsEntry
	   ACCESS                               not-accessible
	   STATUS                               mandatory
	   DESCRIPTION
	    "A List of Driver Generic Statistics"
	   ::= { nicStatistics 1 }
	   
	nicStatisticsEntry              OBJECT-TYPE
		SYNTAX                          NicStatisticsEntry
		ACCESS                          not-accessible
		STATUS                          mandatory
		DESCRIPTION
		 "An entry in the Generic Statistics Table."
		INDEX                           { nicStatisticsIndex }
		::= { nicStatisticsTable 1 }
	
	-- name the elements in the table
		
	NicStatisticsEntry              ::=
							SEQUENCE {
							nicStatisticsIndex
									INTEGER,
							nicTtlTxPacket
									Counter,
							nicDeltaTtlTxPacket
									INTEGER,
							nicTtlRxPacket
									Counter,
							nicDeltaTtlRxPacket
									INTEGER,
							nicGetECBFails
									Counter,
							nicTxTooBig
									Counter,
							nicRxTooBig
									Counter,                
							nicRxOverflow
									Counter,
							nicTxMisc
									Counter,
							nicRxMisc
									Counter,
							nicRxCRC
									Counter,
							nicTxOKByte
									Counter,
							nicDeltaTxOKByte
									INTEGER,
							nicRxOKByte
									Counter,
							nicDeltaRxOKByte
									INTEGER,
							nicTxGroup
									Counter,
							nicDeltaTxGroup
									INTEGER,
							nicRxGroup
									Counter,
							nicDeltaRxGroup
									INTEGER,
							nicAdapterReset
									Counter,
							nicQDepth
									Counter,
							nicRcvBuffers
									Counter,
							nicRcvBuffers75Pct
									Counter,
							nicRcvBuffersCkOut
									Counter,
							nicRcvBuffersMaxSize
									INTEGER,
							nicNumCustCounter
									INTEGER                 
							}
							
	-- define each element
	
	nicStatisticsIndex              OBJECT-TYPE
	    SYNTAX                              INTEGER
	    ACCESS                              read-only
	    STATUS                              mandatory
	    DESCRIPTION
	     "Index into the Generic Statistics Table."
	    ::= { nicStatisticsEntry 1 }  

	nicTtlTxPacket          OBJECT-TYPE
	   SYNTAX               Counter
	   ACCESS               read-only
	   STATUS               mandatory
	   DESCRIPTION
		"Number of packets transmitted successfully"
	   ::= {nicStatisticsEntry 2}

	nicDeltaTtlTxPacket     OBJECT-TYPE
	   SYNTAX               INTEGER
	   ACCESS               read-only
	   STATUS               mandatory
	   DESCRIPTION
		"Number of packets transmitted Between last read
		and current time"
	   ::= {nicStatisticsEntry 3}

	nicTtlRxPacket          OBJECT-TYPE
	   SYNTAX               Counter
	   ACCESS               read-only
	   STATUS               mandatory
	   DESCRIPTION
		"Number of packets received successfully"
	   ::= {nicStatisticsEntry 4}

	nicDeltaTtlRxPacket     OBJECT-TYPE
	   SYNTAX               INTEGER
	   ACCESS               read-only
	   STATUS               mandatory
	   DESCRIPTION
		"Number of packets received between last
		 update and current time"
	   ::= {nicStatisticsEntry 5}

	nicGetECBFails          OBJECT-TYPE
	   SYNTAX               Counter
	   ACCESS               read-only
	   STATUS               mandatory
	   DESCRIPTION
		"Number of times an ECB request failed"
	   ::= {nicStatisticsEntry 6}
	   
	nicTxTooBig             OBJECT-TYPE
	   SYNTAX               Counter
	   ACCESS               read-only
	   STATUS               mandatory
	   DESCRIPTION
		"Number of packets that are too big for
		 transmission"
	   ::= {nicStatisticsEntry 7}

	nicRxTooBig             OBJECT-TYPE
	   SYNTAX               Counter
	   ACCESS               read-only
	   STATUS               mandatory
	   DESCRIPTION
		"Number of packets that are too big for
		 receive buffer"
	   ::= {nicStatisticsEntry 8}   
	   
	nicRxOverflow                   OBJECT-TYPE
	   SYNTAX                               Counter
	   ACCESS                               read-only
	   STATUS                               mandatory
	   DESCRIPTION
			"Number of missed packets"
		::= {nicStatisticsEntry 9}   

	nicTxMisc               OBJECT-TYPE
	   SYNTAX               Counter
	   ACCESS               read-only
	   STATUS               mandatory
	   DESCRIPTION
		"Number of packets with fatal transmission errors that
		 are not accounted for anywhere else"
	   ::= {nicStatisticsEntry 10}

	nicRxMisc               OBJECT-TYPE
	   SYNTAX               Counter
	   ACCESS               read-only
	   STATUS               mandatory
	   DESCRIPTION
		"Number of packets with fatal receive errors that
		 are not accounted for anywhere else"
	   ::= {nicStatisticsEntry 11}

	nicRxCRC                OBJECT-TYPE
	   SYNTAX               Counter
	   ACCESS               read-only
	   STATUS               mandatory
	   DESCRIPTION
		"Number of packets received with corrupt data"
	   ::= {nicStatisticsEntry 12}

	
	nicTxOKByte             OBJECT-TYPE
	   SYNTAX               Counter
	   ACCESS               read-only
	   STATUS               mandatory
	   DESCRIPTION
		"Number of bytes transmitted successfully"
	   ::= {nicStatisticsEntry 13}

	nicDeltaTxOKByte        OBJECT-TYPE
	   SYNTAX               INTEGER
	   ACCESS               read-only
	   STATUS               mandatory
	   DESCRIPTION
		"Number of bytes transmitted between the last
		 update and current time"
	   ::= {nicStatisticsEntry 14}
	
	nicRxOKByte             OBJECT-TYPE
	   SYNTAX               Counter
	   ACCESS               read-only
	   STATUS               mandatory
	   DESCRIPTION
		"Number of bytes received successfully"
	   ::= {nicStatisticsEntry 15}

	nicDeltaRxOKByte        OBJECT-TYPE
	   SYNTAX               INTEGER
	   ACCESS               read-only
	   STATUS               mandatory
	   DESCRIPTION
		"Number of bytes received between the last
		 update and current time"
	   ::= {nicStatisticsEntry 16}
	
	nicTxGroup              OBJECT-TYPE
	   SYNTAX               Counter
	   ACCESS               read-only
	   STATUS               mandatory
	   DESCRIPTION
		"Number of packets transmitted with group addressing"
	   ::= {nicStatisticsEntry 17}

	nicDeltaTxGroup         OBJECT-TYPE
	   SYNTAX               INTEGER
	   ACCESS               read-only
	   STATUS               mandatory
	   DESCRIPTION
		"Number of packets transmitted with group addressing
		 between the last update and current time"
	   ::= {nicStatisticsEntry 18}
	
	nicRxGroup              OBJECT-TYPE
	   SYNTAX               Counter
	   ACCESS               read-only
	   STATUS               mandatory
	   DESCRIPTION
		"Number of packets received with group addressing"
	   ::= {nicStatisticsEntry 19}

	nicDeltaRxGroup         OBJECT-TYPE
	   SYNTAX               INTEGER
	   ACCESS               read-only
	   STATUS               mandatory
	   DESCRIPTION
		"Number of packets received with group addressing
		 between the last update and current time"
	   ::= {nicStatisticsEntry 20}
	
	nicAdapterReset         OBJECT-TYPE
	   SYNTAX               Counter
	   ACCESS               read-only
	   STATUS               mandatory
	   DESCRIPTION
		"Number of times the adapter reset due to internal errors"
	   ::= {nicStatisticsEntry 21}

	nicQDepth               OBJECT-TYPE
	   SYNTAX               Counter
	   ACCESS               read-only
	   STATUS               mandatory
	   DESCRIPTION
		"Number of transmit ECBs queued for the adapter"
	   ::= {nicStatisticsEntry 22}

	nicRcvBuffers           OBJECT-TYPE
	   SYNTAX               Counter
	   ACCESS               read-only
	   STATUS               mandatory
	   DESCRIPTION
		"Number of LSL receive buffers"
	   ::= {nicStatisticsEntry 23}
	
	nicRcvBuffers75Pct      OBJECT-TYPE
	   SYNTAX               Counter
	   ACCESS               read-only
	   STATUS               mandatory
	   DESCRIPTION
		"Number of LSL receive buffers that must be
		 in use before buffers are regarded as getting 
		 low"
	   ::= {nicStatisticsEntry 24}

	nicRcvBuffersCkOut      OBJECT-TYPE
	   SYNTAX               Counter
	   ACCESS               read-only
	   STATUS               mandatory
	   DESCRIPTION
		"Number of buffers in use"
	   ::= {nicStatisticsEntry 25}

	nicRcvBuffersMaxSize    OBJECT-TYPE
	   SYNTAX               INTEGER
	   ACCESS               read-only
	   STATUS               mandatory
	   DESCRIPTION
		"Size of data portion of the ECB in bytes"
	   ::= {nicStatisticsEntry 26}

	nicNumCustCounter       OBJECT-TYPE
	   SYNTAX               INTEGER
	   ACCESS               read-only
	   STATUS               mandatory
	   DESCRIPTION
		"Number of Driver Custom Counters"
	   ::= {nicStatisticsEntry 27}


	-- the NIC Driver Custom Statistic Table 
	
	nicCustStatTable                                 OBJECT-TYPE
	   SYNTAX                                                SEQUENCE OF NicCustEntry
	   ACCESS                                                not-accessible
	   STATUS                                                mandatory
	   DESCRIPTION
		    "A list of Driver Custom Statistics"
	   ::= {nicCustomStats 1}
	
	nicCustEntry                                     OBJECT-TYPE
		SYNTAX                                       NicCustEntry
		ACCESS                                       not-accessible
		STATUS                                       mandatory
		DESCRIPTION
			 "An entry in the driver custom statistic table"
		INDEX { nicCustIndex, nicIndex }
		::= {nicCustStatTable 1}
		
	-- name the elements in the table
	
	NicCustEntry    ::=
		SEQUENCE {
		  nicCustIndex
				INTEGER,
		  nicIndex
				INTEGER,
		  nicCustCounter
				Counter,
		  nicCustCounterString
				DisplayString
		  }
		  
	-- define each element
	
	nicCustIndex                                                                    OBJECT-TYPE
	   SYNTAX                                                                               INTEGER
	   ACCESS                                                                               read-only
	   STATUS                                                                               mandatory
	   DESCRIPTION
	    "Index of list of lan adapters."
	   ::= { nicCustEntry 1 }
	   
	nicIndex                                        OBJECT-TYPE
	   SYNTAX                                       INTEGER
	   ACCESS                                       read-only
	   STATUS                                       mandatory
	   DESCRIPTION
		    "Index into the list of driver 
		    custom statistics table"
	   ::= {nicCustEntry 2}
					    
	nicCustCounter                  OBJECT-TYPE
	   SYNTAX                        Counter
	   ACCESS                        read-only
	   STATUS                        mandatory
	   DESCRIPTION
		"The counter for a custom statistic"
	
	   ::= {nicCustEntry 3}

	nicCustCounterString            OBJECT-TYPE
	   SYNTAX                        DisplayString (SIZE (0..80))
	   ACCESS                        read-only
	   STATUS                        mandatory
	   DESCRIPTION
		"Name of the custom counter"
	   ::= {nicCustEntry 4}


	-- NIC Error Statistic (Media Specific) Table

	nicErrorsTable                                  OBJECT-TYPE
	   SYNTAX                                               SEQUENCE OF NicErrorsEntry
	   ACCESS                                               not-accessible
	   STATUS                                               mandatory
	   DESCRIPTION
	    "A list of Driver Error Statistics."
	   ::= { nicErrors 1 }
	   
	nicErrorsEntry                                  OBJECT-TYPE
	   SYNTAX                                               NicErrorsEntry
	   ACCESS                                               not-accessible
	   STATUS                                               mandatory
	   DESCRIPTION
	    "an entry in the driver errors statistics table."
	   INDEX { nicErrorsIndex }
	   ::= { nicErrorsTable 1 }
	  
	-- Name the elements in the Table
	
	NicErrorsEntry                                  ::=
									SEQUENCE {
									nicErrorsIndex
											INTEGER,
									nicTxOKSingleCollision
											Counter,
									nicTxOKMultipleCollision
											Counter,
									nicTxOKDeferred
											Counter,
									nicTxAbortLateCollision
											Counter,
									nicTxAbortExcessCollision
											Counter,
									nicTxAbortCarrierSense
											Counter,
									nicTxAbortExcessiveDeferral
											Counter,
									nicRxAbortFrameAlignment
											Counter,
									nicHWRxMismatch
											Counter,
									nicTtlTxErrPacket
											INTEGER,
									nicTtlRxErrPacket
											INTEGER                                                                                                                                                                                 
									}
									
	-- define each element
	
	nicErrorsIndex                                  OBJECT-TYPE
	   SYNTAX                                               INTEGER
	   ACCESS                                               read-only
	   STATUS                                               mandatory
	   DESCRIPTION
	    "Index into the error statistics Table."
	   ::= { nicErrorsEntry 1 }
	   
	nicTxOKSingleCollision          OBJECT-TYPE
	   SYNTAX                       Counter
	   ACCESS                       read-only
	   STATUS                       mandatory
	   DESCRIPTION
		"Number of frames involved in a single collision 
		 that are subsequently transmitted successfully"
	   ::= {nicErrorsEntry 2}

	nicTxOKMultipleCollision          OBJECT-TYPE
	   SYNTAX                         Counter
	   ACCESS                         read-only
	   STATUS                         mandatory
	   DESCRIPTION
		"Number of frames involved in more than one collision 
		 that are subsequently transmitted successfully"
	   ::= {nicErrorsEntry 3}

	nicTxOKDeferred             OBJECT-TYPE
	   SYNTAX                   Counter
	   ACCESS                   read-only
	   STATUS                   mandatory
	   DESCRIPTION
		"Number of frames whose transmission was delayed on
		 the first attempt because media was busy"
	   ::= {nicErrorsEntry 4}

	nicTxAbortLateCollision             OBJECT-TYPE
	   SYNTAX                           Counter
	   ACCESS                           read-only
	   STATUS                           mandatory
	   DESCRIPTION
		"Number of collisions detected later than 512 bit times
		 into the tranmitted packet"
	   ::= {nicErrorsEntry 5}

	nicTxAbortExcessCollision               OBJECT-TYPE
	   SYNTAX                               Counter
	   ACCESS                               read-only
	   STATUS                               mandatory
	   DESCRIPTION
		"Number of frames not transmitted successfully due
		 to excessive collision"
	   ::= {nicErrorsEntry 6}

	nicTxAbortCarrierSense               OBJECT-TYPE
	   SYNTAX                            Counter
	   ACCESS                            read-only
	   STATUS                            mandatory
	   DESCRIPTION
		"Number of times the carrierSense variable was
		 not asserted or was deasserted during transmission
		 of a frame without collision"
	   ::= {nicErrorsEntry 7}

	nicTxAbortExcessiveDeferral             OBJECT-TYPE
	   SYNTAX                               Counter
	   ACCESS                               read-only
	   STATUS                               mandatory
	   DESCRIPTION
		"Number of frames deferred for an excessive period
		 of time"
	   ::= {nicErrorsEntry 8}

	nicRxAbortFrameAlignment             OBJECT-TYPE
	   SYNTAX                            Counter
	   ACCESS                            read-only
	   STATUS                            mandatory
	   DESCRIPTION
		"Number of frames that are not an integral number
		 of octets in length and do not pass the FCS check"
	   ::= {nicErrorsEntry 9}

	nicHWRxMismatch             OBJECT-TYPE
	   SYNTAX                   Counter
	   ACCESS                   read-only
	   STATUS                   mandatory
	   DESCRIPTION
		"Number of packets received that did not pass the 
		 length consistency checks" 
	   ::= {nicErrorsEntry 10}

	nicTtlTxErrPacket                       OBJECT-TYPE
		SYNTAX                                  INTEGER
		ACCESS                                  read-only
		STATUS                                  mandatory
		DESCRIPTION
		 "Total Number of packets with transmission errors"
		::= {nicErrorsEntry 11}
		
	nicTtlRxErrPacket                       OBJECT-TYPE
		SYNTAX                                  INTEGER
		ACCESS                                  read-only
		STATUS                                  mandatory
		DESCRIPTION
		 "Total Number of packets with receive errors"
		::= {nicErrorsEntry 12}
		
	-- Miscellaneous information for NIC Agent
	
	nicNumBoards            OBJECT-TYPE
	   SYNTAX               INTEGER
	   ACCESS               read-only
	   STATUS               mandatory
	   DESCRIPTION
		"Total number of adapters installed in the system"
	   ::= { nicMiscellaneous 1 }
	
	nicAdapterType          OBJECT-TYPE
	   SYNTAX               INTEGER
	   ACCESS               read-only
	   STATUS               mandatory
	   DESCRIPTION
		"Type of adapter that the user is currently looking at"
	   ::= { nicMiscellaneous 2 }

	-- the NIC Frame Type Table 
	
	nicFrameTypeTable                                 OBJECT-TYPE
	   SYNTAX                                         SEQUENCE OF NicFrameTypeEntry
	   ACCESS                                         not-accessible
	   STATUS                                         mandatory
	   DESCRIPTION
		    "A list of Frame Types supported by the Driver"
	   ::= {nicFrameType 1}
	
	nicFrameTypeEntry                                OBJECT-TYPE
		SYNTAX                                       NicFrameTypeEntry
		ACCESS                                       not-accessible
		STATUS                                       mandatory
		DESCRIPTION
			 "An entry in the driver Frame Type table"
		INDEX { nicFrameTypeIndex, nicCardIndex }
		::= {nicFrameTypeTable 1}
		
	-- name the elements in the table
	
	NicFrameTypeEntry    ::=
		SEQUENCE {
		  nicFrameTypeIndex
				INTEGER,
		  nicCardIndex
				INTEGER,
		  nicFrameTypeString
				DisplayString
		  }
		  
	-- define each element
	
	nicFrameTypeIndex                                                       OBJECT-TYPE
	   SYNTAX                                                                       INTEGER
	   ACCESS                                                                       read-only
	   STATUS                                                                       mandatory
	   DESCRIPTION
	    "Index into a list of supported frame types."
	   ::= { nicFrameTypeEntry 1 }
	   
	nicCardIndex                                    OBJECT-TYPE
	   SYNTAX                                       INTEGER
	   ACCESS                                       read-only
	   STATUS                                       mandatory
	   DESCRIPTION
		    "Index of list of lan adapters."
	   ::= {nicFrameTypeEntry 2}
					    
	nicFrameTypeString            OBJECT-TYPE
	   SYNTAX                     DisplayString (SIZE (0..80))
	   ACCESS                     read-only
	   STATUS                     mandatory
	   DESCRIPTION
		"Name of the frame type such as Ethernet_802.2"
	   ::= {nicFrameTypeEntry 3}
	      
	-- NIC Agent Parameters

	nicParmSampling         OBJECT-TYPE
	   SYNTAX               INTEGER
	   ACCESS               read-write
	   STATUS               mandatory
	   DESCRIPTION
		"User configurable data sampling time,
		 default once per 5 seconds"
	   ::= { nicCommonParms 1 }

	nicParmProcessing       OBJECT-TYPE
	   SYNTAX               INTEGER
	   ACCESS               read-write
	   STATUS               mandatory
	   DESCRIPTION
		"User configurable data processing time,
		 default once per minute"
	   ::= { nicCommonParms 2 }

	nicParmRxErrCount       OBJECT-TYPE
	   SYNTAX               INTEGER
	   ACCESS               read-write
	   STATUS               mandatory
	   DESCRIPTION
		"User configurable threshold for receive errors" 
	   ::= { nicCommonParms 3 }

	nicParmRxErrDelta       OBJECT-TYPE
	   SYNTAX               INTEGER
	   ACCESS               read-write
	   STATUS               mandatory
	   DESCRIPTION
		"User configurable threshold for receive errors
		 between last update and current time" 
	   ::= { nicCommonParms 4 }
	
	nicParmRxErrPct         OBJECT-TYPE
	   SYNTAX               DisplayString (SIZE(0..10))
	   ACCESS               read-write
	   STATUS               mandatory
	   DESCRIPTION
		"User configurable threshold for receive errors, 
		 this is a relative count"
	   ::= { nicCommonParms 5 }

	nicParmTxErrCount       OBJECT-TYPE
	   SYNTAX               INTEGER
	   ACCESS               read-write
	   STATUS               mandatory
	   DESCRIPTION
		"User configurable threshold for transmit errors"
	   ::= { nicCommonParms 6 }

	nicParmTxErrDelta       OBJECT-TYPE
	   SYNTAX               INTEGER
	   ACCESS               read-write
	   STATUS               mandatory
	   DESCRIPTION
		"User configurable threshold for transmit errors
		 between the last update and current time"
	   ::= { nicCommonParms 7 }
	
	nicParmTxErrPct         OBJECT-TYPE
	   SYNTAX               DisplayString(SIZE(0..10))
	   ACCESS               read-write
	   STATUS               mandatory
	   DESCRIPTION
		"User configurable threshold for transmit errors,
		 this is a relative count"
	   ::= { nicCommonParms 8 }
	
	nicParmAdapterResetCount        OBJECT-TYPE
	   SYNTAX                       INTEGER
	   ACCESS                       read-write
	   STATUS                       mandatory
	   DESCRIPTION
		"User configurable threshold for Adapter Reset errors"
	   ::= { nicCommonParms 9 }

	nicParmAdapterResetDelta        OBJECT-TYPE
	   SYNTAX                       INTEGER
	   ACCESS                       read-write
	   STATUS                       mandatory
	   DESCRIPTION
		"User configurable threshold for Adapter Reset errors
		 between the last update and current time"
	   ::= { nicCommonParms 10 }
	
	nicParmAdapterResetPct          OBJECT-TYPE
	   SYNTAX                       DisplayString(SIZE(0..10))
	   ACCESS                       read-write
	   STATUS                       mandatory
	   DESCRIPTION
		"User configurable threshold for Adapter Reset errors,
		 this is a relative count"
	   ::= { nicCommonParms 11 }
	

	nicParmAlignmentCount        OBJECT-TYPE
	   SYNTAX                    INTEGER
	   ACCESS                    read-write
	   STATUS                    mandatory
	   DESCRIPTION
		"User configurable threshold for Alignment errors"
	   ::= { nicCommonParms 12 }

	nicParmAlignmentDelta        OBJECT-TYPE
	   SYNTAX                    INTEGER
	   ACCESS                    read-write
	   STATUS                    mandatory
	   DESCRIPTION
		"User configurable threshold for Alignment errors
		 between the last update and current time"
	   ::= { nicCommonParms 13 }

	nicParmAlignmentPct          OBJECT-TYPE
	   SYNTAX                    DisplayString(SIZE(0..10))
	   ACCESS                    read-write
	   STATUS                    mandatory
	   DESCRIPTION
		"User configurable threshold for Alignment errors,
		 this is a relative count"
	   ::= { nicCommonParms 14 }
	
	nicParmFrameTooLongCount        OBJECT-TYPE
	   SYNTAX                       INTEGER
	   ACCESS                       read-write
	   STATUS                       mandatory
	   DESCRIPTION
		"User configurable threshold for Frame Too Long errors"
	   ::= { nicCommonParms 15 }

	nicParmFrameTooLongDelta        OBJECT-TYPE
	   SYNTAX                       INTEGER
	   ACCESS                       read-write
	   STATUS                       mandatory
	   DESCRIPTION
		"User configurable threshold for Frame Too Long errors
		 between the last update and current time"
	   ::= { nicCommonParms 16 }

	nicParmFrameTooLongPct          OBJECT-TYPE
	   SYNTAX                       DisplayString(SIZE(0..10))
	   ACCESS                       read-write
	   STATUS                       mandatory
	   DESCRIPTION
		"User configurable threshold for Frame Too Long errors,
		 this is a relative count"
	   ::= { nicCommonParms 17 }
	
	nicParmHardwareMismatchCount            OBJECT-TYPE
	   SYNTAX                               INTEGER
	   ACCESS                               read-write
	   STATUS                               mandatory
	   DESCRIPTION
		"User configurable threshold for Hardware Mismatch errors"
	   ::= { nicCommonParms 18 }

	nicParmHardwareMismatchDelta            OBJECT-TYPE
	   SYNTAX                               INTEGER
	   ACCESS                               read-write
	   STATUS                               mandatory
	   DESCRIPTION
		"User configurable threshold for Hardware Mismatch errors
		 between the last update and current time"
	   ::= { nicCommonParms 19 }

	nicParmHardwareMismatchPct              OBJECT-TYPE
	   SYNTAX                               DisplayString(SIZE(0..10))
	   ACCESS                               read-write
	   STATUS                               mandatory
	   DESCRIPTION
		"User configurable threshold for Hardware Mismatch errors,
		 this is a relative count"
	   ::= { nicCommonParms 20 }
	
	nicParmLateCollisionCount       OBJECT-TYPE
	   SYNTAX                       INTEGER
	   ACCESS                       read-write
	   STATUS                       mandatory
	   DESCRIPTION
		"User configurable threshold for Late Collision errors"
	   ::= { nicCommonParms 21 }

	nicParmLateCollisionDelta       OBJECT-TYPE
	   SYNTAX                       INTEGER
	   ACCESS                       read-write
	   STATUS                       mandatory
	   DESCRIPTION
		"User configurable threshold for Late Collision errors
		 between the last update and current time"
	   ::= { nicCommonParms 22 }
	
	nicParmLateCollisionPct         OBJECT-TYPE
	   SYNTAX                       DisplayString(SIZE(0..10))
	   ACCESS                       read-write
	   STATUS                       mandatory
	   DESCRIPTION
		"User configurable threshold for Late Collision errors,
		 this is a relative count"
	   ::= { nicCommonParms 23 }

	nicParmExcessCollisionCount     OBJECT-TYPE
	   SYNTAX                       INTEGER
	   ACCESS                       read-write
	   STATUS                       mandatory
	   DESCRIPTION
		"User configurable threshold for Excessive Collision errors"
	   ::= { nicCommonParms 24 }

	nicParmExcessCollisionDelta     OBJECT-TYPE
	   SYNTAX                       INTEGER
	   ACCESS                       read-write
	   STATUS                       mandatory
	   DESCRIPTION
		"User configurable threshold for Excessive Collision errors
		 between the last update and current time"
	   ::= { nicCommonParms 25 }
	
	nicParmExcessCollisionPct       OBJECT-TYPE
	   SYNTAX                       DisplayString(SIZE(0..10))
	   ACCESS                       read-write
	   STATUS                       mandatory
	   DESCRIPTION
		"User configurable threshold for Excess Collision errors,
		 this is a relative count"
	   ::= { nicCommonParms 26 }

	nicParmCarrierSenseCount        OBJECT-TYPE
	   SYNTAX                       INTEGER
	   ACCESS                       read-write
	   STATUS                       mandatory
	   DESCRIPTION
		"User configurable threshold for Carrier Sense errors"
	   ::= { nicCommonParms 27 }

	nicParmCarrierSenseDelta        OBJECT-TYPE
	   SYNTAX                       INTEGER
	   ACCESS                       read-write
	   STATUS                       mandatory
	   DESCRIPTION
		"User configurable threshold for Carrier Sense errors
		 between the last update and current time"
	   ::= { nicCommonParms 28 }

	nicParmCarrierSensePct          OBJECT-TYPE
	   SYNTAX                       DisplayString(SIZE(0..10))
	   ACCESS                       read-write
	   STATUS                       mandatory
	   DESCRIPTION
		"User configurable threshold for Carrier Sense errors,
		 this is a relative count"
	   ::= { nicCommonParms 29}

	nicParmDeferralCount            OBJECT-TYPE
	   SYNTAX                       INTEGER
	   ACCESS                       read-write
	   STATUS                       mandatory
	   DESCRIPTION
		"User configurable threshold for Deferral errors"
	   ::= { nicCommonParms 30 }

	nicParmDeferralDelta            OBJECT-TYPE
	   SYNTAX                       INTEGER
	   ACCESS                       read-write
	   STATUS                       mandatory
	   DESCRIPTION
		"User configurable threshold for Deferral errors
		 between the last update and current time"
	   ::= { nicCommonParms 31 }

	nicParmDeferralPct              OBJECT-TYPE
	   SYNTAX                       DisplayString(SIZE(0..10))
	   ACCESS                       read-write
	   STATUS                       mandatory
	   DESCRIPTION
		"User configurable threshold for Deferral errors,
		 this is a relative count"
	   ::= { nicCommonParms 32 }
	   
	nicParmNoECBCount            OBJECT-TYPE
	   SYNTAX                       INTEGER
	   ACCESS                       read-write
	   STATUS                       mandatory
	   DESCRIPTION
		"User configurable threshold for Deferral errors"
	   ::= { nicCommonParms 33 }

	nicParmNoECBDelta            OBJECT-TYPE
	   SYNTAX                       INTEGER
	   ACCESS                       read-write
	   STATUS                       mandatory
	   DESCRIPTION
		"User configurable threshold for Deferral errors
		 between the last update and current time"
	   ::= { nicCommonParms 34 } 
	   
	nicParmNoECBPct              OBJECT-TYPE
	   SYNTAX                       DisplayString(SIZE(0..10))
	   ACCESS                       read-write
	   STATUS                       mandatory
	   DESCRIPTION
		"User configurable threshold for Deferral errors,
		 this is a relative count"
	   ::= { nicCommonParms 35 }
	   
	nicParmRxOverflowCount            OBJECT-TYPE
	   SYNTAX                       INTEGER
	   ACCESS                       read-write
	   STATUS                       mandatory
	   DESCRIPTION
		"User configurable threshold for Deferral errors"
	   ::= { nicCommonParms 36 }

	nicParmRxOverflowDelta            OBJECT-TYPE
	   SYNTAX                       INTEGER
	   ACCESS                       read-write
	   STATUS                       mandatory
	   DESCRIPTION
		"User configurable threshold for Deferral errors
		 between the last update and current time"
	   ::= { nicCommonParms 37 }

	nicParmRxOverflowPct              OBJECT-TYPE
	   SYNTAX                       DisplayString(SIZE(0..10))
	   ACCESS                       read-write
	   STATUS                       mandatory
	   DESCRIPTION
		"User configurable threshold for Deferral errors,
		 this is a relative count"
	   ::= { nicCommonParms 38 }

	nicParmUtilizationCount         OBJECT-TYPE
	   SYNTAX                       INTEGER
	   ACCESS                       read-write
	   STATUS                       mandatory
	   DESCRIPTION
		"User configurable threshold for packets or bytes/second
		 utilization"
	   ::= { nicCommonParms 39 }

	nicParmAdapterType              OBJECT-TYPE
	   SYNTAX                       INTEGER
	   ACCESS                       read-write
	   STATUS                       mandatory
	   DESCRIPTION
		"User selected Adapter Type, will generate an alarm
		 if there is a mismatch" 
	   ::= { nicCommonParms 40 }
 
	nicParmLineErrCount             OBJECT-TYPE
	   SYNTAX                       INTEGER
	   ACCESS                       read-write
	   STATUS                       mandatory
	   DESCRIPTION
		"User configurable threshold for Token Ring Line errors"
	   ::= { nicCommonParms 41 }

	nicParmLineErrDelta             OBJECT-TYPE
	   SYNTAX                       INTEGER
	   ACCESS                       read-write
	   STATUS                       mandatory
	   DESCRIPTION
		"User configurable threshold for Token Ring Line errors
		 between the last update and current time"
	   ::= { nicCommonParms 42 }

	nicParmLineErrPct               OBJECT-TYPE
	   SYNTAX                       DisplayString(SIZE(0..10))
	   ACCESS                       read-write
	   STATUS                       mandatory
	   DESCRIPTION
		"User configurable threshold for Token Ring Line errors,
		 this is a relative count"
	   ::= { nicCommonParms 43 }

	nicParmLostFramesCount          OBJECT-TYPE
	   SYNTAX                       INTEGER
	   ACCESS                       read-write
	   STATUS                       mandatory
	   DESCRIPTION
		"User configurable threshold for Token Ring Lost Frames"
	   ::= { nicCommonParms 44 }

	nicParmLostFramesDelta          OBJECT-TYPE
	   SYNTAX                       INTEGER
	   ACCESS                       read-write
	   STATUS                       mandatory
	   DESCRIPTION
		"User configurable threshold for Token Ring Lost Frames
		 between the last update and current time"
	   ::= { nicCommonParms 45 }

	nicParmLostFramesPct            OBJECT-TYPE
	   SYNTAX                       DisplayString(SIZE(0..10))
	   ACCESS                       read-write
	   STATUS                       mandatory
	   DESCRIPTION
		"User configurable threshold for Token Ring Lost Frames,
		 this is a relative count"
	   ::= { nicCommonParms 46 }

	nicParmBurstErrCount            OBJECT-TYPE
	   SYNTAX                       INTEGER
	   ACCESS                       read-write
	   STATUS                       mandatory
	   DESCRIPTION
		"User configurable threshold for Token Ring Burst errors"
	   ::= { nicCommonParms 47 }

	nicParmBurstErrDelta            OBJECT-TYPE
	   SYNTAX                       INTEGER
	   ACCESS                       read-write
	   STATUS                       mandatory
	   DESCRIPTION
		"User configurable threshold for Token Ring Burst errors
		 between the last update and current time"
	   ::= { nicCommonParms 48 }

	nicParmBurstErrPct              OBJECT-TYPE
	   SYNTAX                       DisplayString(SIZE(0..10))
	   ACCESS                       read-write
	   STATUS                       mandatory
	   DESCRIPTION
		"User configurable threshold for Token Ring Burst errors,
		 this is a relative count"
	   ::= { nicCommonParms 49 }

	nicParmACErrCount               OBJECT-TYPE
	   SYNTAX                       INTEGER
	   ACCESS                       read-write
	   STATUS                       mandatory
	   DESCRIPTION
		"User configurable threshold for Token Ring A/C errors"
	   ::= { nicCommonParms 50 }

	nicParmACErrDelta               OBJECT-TYPE
	   SYNTAX                       INTEGER
	   ACCESS                       read-write
	   STATUS                       mandatory
	   DESCRIPTION
		"User configurable threshold for Token Ring A/C errors
		 between the last update and current time"
	   ::= { nicCommonParms 51 }

	nicParmACErrPct                 OBJECT-TYPE
	   SYNTAX                       DisplayString(SIZE(0..10))
	   ACCESS                       read-write
	   STATUS                       mandatory
	   DESCRIPTION
		"User configurable threshold for Token Ring A/C errors,
		 this is a relative count"
	   ::= { nicCommonParms 52 }

	nicParmAbortDelimitersCount     OBJECT-TYPE
	   SYNTAX                       INTEGER
	   ACCESS                       read-write
	   STATUS                       mandatory
	   DESCRIPTION
		"User configurable threshold for Token Ring Abort Delimiters"
	   ::= { nicCommonParms 53 }

	nicParmAbortDelimitersDelta     OBJECT-TYPE
	   SYNTAX                       INTEGER
	   ACCESS                       read-write
	   STATUS                       mandatory
	   DESCRIPTION
		"User configurable threshold for Token Ring Abort Delimiters
		 between the last update and current time"
	   ::= { nicCommonParms 54 }

	nicParmAbortDelimitersPct       OBJECT-TYPE
	   SYNTAX                       DisplayString(SIZE(0..10))
	   ACCESS                       read-write
	   STATUS                       mandatory
	   DESCRIPTION
		"User configurable threshold for Token Ring Abort Delimiters,
		 this is a relative count"
	   ::= { nicCommonParms 55 }

	nicParmFrameCopiedErrCount      OBJECT-TYPE
	   SYNTAX                       INTEGER
	   ACCESS                       read-write
	   STATUS                       mandatory
	   DESCRIPTION
		"User configurable threshold for Token Ring Frame Copied errors"
	   ::= { nicCommonParms 56 }

	nicParmFrameCopiedErrDelta       OBJECT-TYPE
	   SYNTAX                       INTEGER
	   ACCESS                       read-write
	   STATUS                       mandatory
	   DESCRIPTION
		"User configurable threshold for Token Ring Frame Copied errors
		 between the last update and current time"
	   ::= { nicCommonParms 57 }

	nicParmFrameCopiedErrPct        OBJECT-TYPE
	   SYNTAX                       DisplayString(SIZE(0..10))
	   ACCESS                       read-write
	   STATUS                       mandatory
	   DESCRIPTION
		"User configurable threshold for Token Ring Frame Copied errors,
		 this is a relative count"
	   ::= { nicCommonParms 58 }

	nicParmFrequencyErrCount        OBJECT-TYPE
	   SYNTAX                       INTEGER
	   ACCESS                       read-write
	   STATUS                       mandatory
	   DESCRIPTION
		"User configurable threshold for Token Ring Frequency errors"
	   ::= { nicCommonParms 59 }

	nicParmFrequencyErrDelta        OBJECT-TYPE
	   SYNTAX                       INTEGER
	   ACCESS                       read-write
	   STATUS                       mandatory
	   DESCRIPTION
		"User configurable threshold for Token Ring Frequency errors
		 between the last update and current time"
	   ::= { nicCommonParms 60 }

	nicParmFrequencyErrPct          OBJECT-TYPE
	   SYNTAX                       DisplayString(SIZE(0..10))
	   ACCESS                       read-write
	   STATUS                       mandatory
	   DESCRIPTION
		"User configurable threshold for Token Ring Frequency errors,
		 this is a relative count"
	   ::= { nicCommonParms 61 }

	nicParmTokenErrCount            OBJECT-TYPE
	   SYNTAX                       INTEGER
	   ACCESS                       read-write
	   STATUS                       mandatory
	   DESCRIPTION
		"User configurable threshold for Token Ring Token errors"
	   ::= { nicCommonParms 62 }

	nicParmTokenErrDelta            OBJECT-TYPE
	   SYNTAX                       INTEGER
	   ACCESS                       read-write
	   STATUS                       mandatory
	   DESCRIPTION
		"User configurable threshold for Token Ring Token errors
		 between the last update and current time"
	   ::= { nicCommonParms 63 }

	nicParmTokenErrPct              OBJECT-TYPE
	   SYNTAX                       DisplayString(SIZE(0..10))
	   ACCESS                       read-write
	   STATUS                       mandatory
	   DESCRIPTION
		"User configurable threshold for Token Ring Token errors,
		 this is a relative count"
	   ::= { nicCommonParms 64 }

	nicParmInternalErrCount         OBJECT-TYPE
	   SYNTAX                       INTEGER
	   ACCESS                       read-write
	   STATUS                       mandatory
	   DESCRIPTION
		"User configurable threshold for Token Ring Internal errors"
	   ::= { nicCommonParms 65 }

	nicParmInternalErrDelta         OBJECT-TYPE
	   SYNTAX                       INTEGER
	   ACCESS                       read-write
	   STATUS                       mandatory
	   DESCRIPTION
		"User configurable threshold for Token Ring Internal errors
		 between the last update and current time"
	   ::= { nicCommonParms 66 }

	nicParmInternalErrPct           OBJECT-TYPE
	   SYNTAX                       DisplayString(SIZE(0..10))
	   ACCESS                       read-write
	   STATUS                       mandatory
	   DESCRIPTION
		"User configurable threshold for Token Ring Internal errors,
		 this is a relative count"
	   ::= { nicCommonParms 67 }

	nicParmAftFailOverErrCount     OBJECT-TYPE
	   SYNTAX                       INTEGER
	   ACCESS                       read-write
	   STATUS                       mandatory
	   DESCRIPTION
		"The active NIC in a redundant group has failed.The standby NIC has taken over."
	   ::= { nicCommonParms 68 }

	nicParmAftFailOverErrDelta     OBJECT-TYPE
	   SYNTAX                       INTEGER
	   ACCESS                       read-write
	   STATUS                       mandatory
	   DESCRIPTION
		"The active NIC in a redundant group has failed.The standby NIC has taken over."
	   ::= { nicCommonParms 69 }


	nicParmAftRecoveryErrCount     OBJECT-TYPE
	   SYNTAX                       INTEGER
	   ACCESS                       read-write
	   STATUS                       mandatory
	   DESCRIPTION
		"The previously failed NIC in a redundant group has become operational."
	   ::= { nicCommonParms 70 }

	nicParmAftRecoveryErrDelta     OBJECT-TYPE
	   SYNTAX                       INTEGER
	   ACCESS                       read-write
	   STATUS                       mandatory
	   DESCRIPTION
		"The previously failed NIC in a redundant group has become operational."
	   ::= { nicCommonParms 71 }

	nicParmAftStandbyErrCount     OBJECT-TYPE
	   SYNTAX                       INTEGER
	   ACCESS                       read-write
	   STATUS                       mandatory
	   DESCRIPTION
		"The standby NIC in a redundant group has failed."
	   ::= { nicCommonParms 72 }

	nicParmAftStandbyErrDelta     OBJECT-TYPE
	   SYNTAX                       INTEGER
	   ACCESS                       read-write
	   STATUS                       mandatory
	   DESCRIPTION
		"The standby NIC in a redundant group has failed."
	   ::= { nicCommonParms 73 }

	nicParmAftGruoupFailErrCount     OBJECT-TYPE
	   SYNTAX                       INTEGER
	   ACCESS                       read-write
	   STATUS                       mandatory
	   DESCRIPTION
		"All NICs (active and standby) in a redundant group have failed."
	   ::= { nicCommonParms 74 }

	nicParmAftGroupFailErrDelta     OBJECT-TYPE
	   SYNTAX                       INTEGER
	   ACCESS                       read-write
	   STATUS                       mandatory
	   DESCRIPTION
		"All NICs (active and standby) in a redundant group have failed."
	   ::= { nicCommonParms 75 }










	-- Starfighter Parameters

	nicStarfighterParmTxFifoCount       OBJECT-TYPE
	   SYNTAX                           INTEGER
	   ACCESS                           read-write
	   STATUS                           mandatory
	   DESCRIPTION
		"User configurable threshold for transmit FIFO 
		 underrun errors" 
	   ::= { nicStarfighterParms 1 }

	nicStarfighterParmTxFifoDelta       OBJECT-TYPE
	   SYNTAX                           INTEGER
	   ACCESS                           read-write
	   STATUS                           mandatory
	   DESCRIPTION
		"User configurable threshold for transmit FIFO 
		 underrun errors between last update and current
		 time" 
	   ::= { nicStarfighterParms 2 }

	nicStarfighterParmTxFifoPct         OBJECT-TYPE
	   SYNTAX                           DisplayString(SIZE(0..10))
	   ACCESS                           read-write
	   STATUS                           mandatory
	   DESCRIPTION
		"User configurable threshold for transmit FIFO  
		 underrun errors, this is a relative count"
	   ::= { nicStarfighterParms 3 }

	nicStarfighterParmTxTimedOutCount       OBJECT-TYPE
	   SYNTAX                               INTEGER
	   ACCESS                               read-write
	   STATUS                               mandatory
	   DESCRIPTION
		"User configurable threshold for transmit timed out"
	   ::= { nicStarfighterParms 4 }

	nicStarfighterParmTxTimedOutDelta       OBJECT-TYPE
	   SYNTAX                               INTEGER
	   ACCESS                               read-write
	   STATUS                               mandatory
	   DESCRIPTION
		"User configurable threshold for transmit timed out"
	   ::= { nicStarfighterParms 5 }

	nicStarfighterParmTxTimedOutPct         OBJECT-TYPE
	   SYNTAX                               DisplayString(SIZE(0..10))
	   ACCESS                               read-write
	   STATUS                               mandatory
	   DESCRIPTION
		"User configurable threshold for transmit timed   
		 out, this is a relative count"
	   ::= { nicStarfighterParms 6 }

	nicStarfighterParmRxFifoCount       OBJECT-TYPE
	   SYNTAX                           INTEGER
	   ACCESS                           read-write
	   STATUS                           mandatory
	   DESCRIPTION
		"User configurable threshold for receive FIFO 
		 overrun errors" 
	   ::= { nicStarfighterParms 7 }

	nicStarfighterParmRxFifoDelta       OBJECT-TYPE
	   SYNTAX                           INTEGER
	   ACCESS                           read-write
	   STATUS                           mandatory
	   DESCRIPTION
		"User configurable threshold for receive FIFO 
		 overrun errors between the last update and 
		 current time" 
	   ::= { nicStarfighterParms 8 }

	nicStarfighterParmRxFifoPct         OBJECT-TYPE
	   SYNTAX                           DisplayString(SIZE(0..10))
	   ACCESS                           read-write
	   STATUS                           mandatory
	   DESCRIPTION
		"User configurable threshold for receive FIFO  
		 overrun errors, this is a relative count"
	   ::= { nicStarfighterParms 9 }

	nicStarfighterParmRxFalseInterruptCount       OBJECT-TYPE
	   SYNTAX                                     INTEGER
	   ACCESS                                     read-write
	   STATUS                                     mandatory
	   DESCRIPTION
		"User configurable threshold for receiver false 
		 interrupts" 
	   ::= { nicStarfighterParms 10 }

	nicStarfighterParmRxFalseInterruptDelta       OBJECT-TYPE
	   SYNTAX                                     INTEGER
	   ACCESS                                     read-write
	   STATUS                                     mandatory
	   DESCRIPTION
		"User configurable threshold for receiver false 
		 interrupts between the last update and current
		 time" 
	   ::= { nicStarfighterParms 11 }

	nicStarfighterParmRxFalseInterruptPct         OBJECT-TYPE
	   SYNTAX                                     DisplayString(SIZE(0..10))
	   ACCESS                                     read-write
	   STATUS                                     mandatory
	   DESCRIPTION
		"User configurable threshold for receive false 
		 interrupts, this is a relative count"
	   ::= { nicStarfighterParms 12 }

	nicStarfighterParmRxPagingErrCount       OBJECT-TYPE
	   SYNTAX                                INTEGER
	   ACCESS                                read-write
	   STATUS                                mandatory
	   DESCRIPTION
		"User configurable threshold for receive paging 
		 errors" 
	   ::= { nicStarfighterParms 13 }

	nicStarfighterParmRxPagingErrDelta       OBJECT-TYPE
	   SYNTAX                                INTEGER
	   ACCESS                                read-write
	   STATUS                                mandatory
	   DESCRIPTION
		"User configurable threshold for receive paging 
		 errors between the last update and current time" 
	   ::= { nicStarfighterParms 14 }
	
	nicStarfighterParmRxPagingErrPct         OBJECT-TYPE
	   SYNTAX                                DisplayString(SIZE(0..10))
	   ACCESS                                read-write
	   STATUS                                mandatory
	   DESCRIPTION
		"User configurable threshold for receive  
		 paging errors, this is a relative count"
	   ::= { nicStarfighterParms 15 }

	
	-- Twister specific user configurable parameters
	
	nicTwisterParmTxFifoCount       OBJECT-TYPE
	   SYNTAX                       INTEGER
	   ACCESS                       read-write
	   STATUS                       mandatory
	   DESCRIPTION
		"User configurable threshold for transmit FIFO 
		 underrun errors" 
	   ::= { nicTwisterParms 1 }

	nicTwisterParmTxFifoDelta       OBJECT-TYPE
	   SYNTAX                       INTEGER
	   ACCESS                       read-write
	   STATUS                       mandatory
	   DESCRIPTION
		"User configurable threshold for transmit FIFO 
		 underrun errors between the last update and 
		 current time" 
	   ::= { nicTwisterParms 2 }

	nicTwisterParmTxFifoPct         OBJECT-TYPE
	   SYNTAX                       DisplayString(SIZE(0..10))
	   ACCESS                       read-write
	   STATUS                       mandatory
	   DESCRIPTION
		"User configurable threshold for transmit FIFO  
		 underrun errors, this is a relative count"
	   ::= { nicTwisterParms 3 }

	nicTwisterParmTxTimedOutCount       OBJECT-TYPE
	   SYNTAX                           INTEGER
	   ACCESS                           read-write
	   STATUS                           mandatory
	   DESCRIPTION
		"User configurable threshold for transmit timed out"
	   ::= { nicTwisterParms 4 }

	nicTwisterParmTxTimedOutDelta       OBJECT-TYPE
	   SYNTAX                           INTEGER
	   ACCESS                           read-write
	   STATUS                           mandatory
	   DESCRIPTION
		"User configurable threshold for transmit timed out
		 between the last update and current time"
	   ::= { nicTwisterParms 5 }

	nicTwisterParmTxTimedOutPct         OBJECT-TYPE
	   SYNTAX                           DisplayString(SIZE(0..10))
	   ACCESS                           read-write
	   STATUS                           mandatory
	   DESCRIPTION
		"User configurable threshold for transmit timed   
		 out, this is a relative count"
	   ::= { nicTwisterParms 6 }

	nicTwisterParmRxFifoCount       OBJECT-TYPE
	   SYNTAX                       INTEGER
	   ACCESS                       read-write
	   STATUS                       mandatory
	   DESCRIPTION
		"User configurable threshold for receive FIFO 
		 overrun errors" 
	   ::= { nicTwisterParms 7 }

	nicTwisterParmRxFifoDelta       OBJECT-TYPE
	   SYNTAX                       INTEGER
	   ACCESS                       read-write
	   STATUS                       mandatory
	   DESCRIPTION
		"User configurable threshold for receive FIFO 
		 overrun errors between the last update and 
		 current time" 
	   ::= { nicTwisterParms 8 }

	nicTwisterParmRxFifoPct         OBJECT-TYPE
	   SYNTAX                       DisplayString(SIZE(0..10))
	   ACCESS                       read-write
	   STATUS                       mandatory
	   DESCRIPTION
		"User configurable threshold for receive FIFO  
		 overrun errors, this is a relative count"
	   ::= { nicTwisterParms 9 }

	nicTwisterParmRxFalseInterruptCount       OBJECT-TYPE
	   SYNTAX                                 INTEGER
	   ACCESS                                 read-write
	   STATUS                                 mandatory
	   DESCRIPTION
		"User configurable threshold for receiver false 
		 interrupts" 
	   ::= { nicTwisterParms 10 }

	nicTwisterParmRxFalseInterruptDelta       OBJECT-TYPE
	   SYNTAX                                 INTEGER
	   ACCESS                                 read-write
	   STATUS                                 mandatory
	   DESCRIPTION
		"User configurable threshold for receiver false 
		 interrupts between the last update and current
		 time" 
	   ::= { nicTwisterParms 11 }

	nicTwisterParmRxFalseInterruptPct         OBJECT-TYPE
	   SYNTAX                                 DisplayString(SIZE(0..10))
	   ACCESS                                 read-write
	   STATUS                                 mandatory
	   DESCRIPTION
		"User configurable threshold for receive false 
		 interrupts, this is a relative count"
	   ::= { nicTwisterParms 12 }

	nicTwisterParmRxPagingErrCount       OBJECT-TYPE
	   SYNTAX                            INTEGER
	   ACCESS                            read-write
	   STATUS                            mandatory
	   DESCRIPTION
		"User configurable threshold for receive paging 
		 errors" 
	   ::= { nicTwisterParms 13 }

	nicTwisterParmRxPagingErrDelta       OBJECT-TYPE
	   SYNTAX                            INTEGER
	   ACCESS                            read-write
	   STATUS                            mandatory
	   DESCRIPTION
		"User configurable threshold for receive paging 
		 errors between the last update and current time" 
	   ::= { nicTwisterParms 14 }

	nicTwisterParmRxPagingErrPct         OBJECT-TYPE
	   SYNTAX                            DisplayString(SIZE(0..10))
	   ACCESS                            read-write
	   STATUS                            mandatory
	   DESCRIPTION
		"User configurable threshold for receive  
		 paging errors, this is a relative count"
	   ::= { nicTwisterParms 15 }

	nicTwisterParmDMATimedOutCount       OBJECT-TYPE
	   SYNTAX                            INTEGER
	   ACCESS                            read-write
	   STATUS                            mandatory
	   DESCRIPTION
		"User configurable threshold for number of times 
		 for DMA timed out" 
	   ::= { nicTwisterParms 16 }

	nicTwisterParmDMATimedOutDelta       OBJECT-TYPE
	   SYNTAX                            INTEGER
	   ACCESS                            read-write
	   STATUS                            mandatory
	   DESCRIPTION
		"User configurable threshold for number of times 
		 for DMA timed out between the last update and
		 current time" 
	   ::= { nicTwisterParms 17 }

	nicTwisterParmDMATimedOutPct         OBJECT-TYPE
	   SYNTAX                            DisplayString(SIZE(0..10))
	   ACCESS                            read-write
	   STATUS                            mandatory
	   DESCRIPTION
		"User configurable threshold for number of times  
		 for DMA timed out, this is a relative count"
	   ::= { nicTwisterParms 18 }

	-- Bus Master user configurable parameters

	nicMasterParmTxNoResourcesCount       OBJECT-TYPE
	   SYNTAX                                 INTEGER
	   ACCESS                                 read-write
	   STATUS                                 mandatory
	   DESCRIPTION
		"User configurable threshold for transmit PDA queue
		 full" 
	   ::= { nicMasterParms 1 }

	nicMasterParmTxNoResourcesDelta           OBJECT-TYPE
	   SYNTAX                                 INTEGER
	   ACCESS                                 read-write
	   STATUS                                 mandatory
	   DESCRIPTION
		"User configurable threshold for transmit PDA queue
		 full between the last update and current time" 
	   ::= { nicMasterParms 2 }

	nicMasterParmTxNoResourcesPct         OBJECT-TYPE
	   SYNTAX                                 DisplayString(SIZE(0..10))
	   ACCESS                                 read-write
	   STATUS                                 mandatory
	   DESCRIPTION
		"User configurable threshold for transmit PDA  
		 queue full, this is a relative count"
	   ::= { nicMasterParms 3 }

	nicMasterParmTxExcessFragsCount       OBJECT-TYPE
	   SYNTAX                                 INTEGER
	   ACCESS                                 read-write
	   STATUS                                 mandatory
	   DESCRIPTION
		"User configurable threshold for excessive
		 transmit fragments"
	   ::= { nicMasterParms 4 }

	nicMasterParmTxExcessFragsDelta       OBJECT-TYPE
	   SYNTAX                                 INTEGER
	   ACCESS                                 read-write
	   STATUS                                 mandatory
	   DESCRIPTION
		"User configurable threshold for excessive
		 transmit fragments between the last update
		 and current time"
	   ::= { nicMasterParms 5 }

	nicMasterParmTxExcessFragsPct         OBJECT-TYPE
	   SYNTAX                                 DisplayString(SIZE(0..10))
	   ACCESS                                 read-write
	   STATUS                                 mandatory
	   DESCRIPTION
		"User configurable threshold for excessive    
		 transmit fragments, this is a relative count"
	   ::= { nicMasterParms 6 }

	nicMasterParmRxLowCount       OBJECT-TYPE
	   SYNTAX                         INTEGER
	   ACCESS                         read-write
	   STATUS                         mandatory
	   DESCRIPTION
		"User configurable threshold for RCBs not allocated"
	   ::= { nicMasterParms 7 }

	nicMasterParmRxLowDelta       OBJECT-TYPE
	   SYNTAX                         INTEGER
	   ACCESS                         read-write
	   STATUS                         mandatory
	   DESCRIPTION
		"User configurable threshold for RCBs not allocated
		 between the last update and current time"
	   ::= { nicMasterParms 8 }

	nicMasterParmRxLowPct         OBJECT-TYPE
	   SYNTAX                         DisplayString(SIZE(0..10))
	   ACCESS                         read-write
	   STATUS                         mandatory
	   DESCRIPTION
		"User configurable threshold for RCBs not allocated,  
		 this is a relative count"
	   ::= { nicMasterParms 9 }

	nicMasterParmRxEmptyCount       OBJECT-TYPE
	   SYNTAX                           INTEGER
	   ACCESS                           read-write
	   STATUS                           mandatory
	   DESCRIPTION
		"User configurable threshold for no RCBs"
	   ::= { nicMasterParms 10 }

	nicMasterParmRxEmptyDelta       OBJECT-TYPE
	   SYNTAX                           INTEGER
	   ACCESS                           read-write
	   STATUS                           mandatory
	   DESCRIPTION
		"User configurable threshold for no RCBs
		 between the last update and current time"
	   ::= { nicMasterParms 11 }

	nicMasterParmRxEmptyPct         OBJECT-TYPE
	   SYNTAX                           DisplayString(SIZE(0..10))
	   ACCESS                           read-write
	   STATUS                           mandatory
	   DESCRIPTION
		"User configurable threshold for no RCBs,  
		 this is a relative count"
	   ::= { nicMasterParms 12 }


	-- Shasta user configurable parameters

	nicShastaParmTxNoResourcesCount       OBJECT-TYPE
	   SYNTAX                                INTEGER
	   ACCESS                                read-write
	   STATUS                                mandatory
	   DESCRIPTION
		"User configurable threshold for transmit PDA queue
		 full" 
	   ::= { nicShastaParms 1 }

	nicShastaParmTxNoResourcesDelta       OBJECT-TYPE
	   SYNTAX                                INTEGER
	   ACCESS                                read-write
	   STATUS                                mandatory
	   DESCRIPTION
		"User configurable threshold for transmit PDA queue
		 full between the last update and current time" 
	   ::= { nicShastaParms 2 }

	nicShastaParmTxNoResourcesPct         OBJECT-TYPE
	   SYNTAX                                DisplayString(SIZE(0..10))
	   ACCESS                                read-write
	   STATUS                                mandatory
	   DESCRIPTION
		"User configurable threshold for transmit PDA  
		 queue full, this is a relative count"
	   ::= { nicShastaParms 3 }

	-- the NIC Token Ring Statistics Table 
	
	nicTokenRingStatisticsTable                       OBJECT-TYPE
	   SYNTAX                                         SEQUENCE OF NicTokenRingStatisticsEntry
	   ACCESS                                         not-accessible
	   STATUS                                         mandatory
	   DESCRIPTION
		"A list of Token Ring statistics supported by the Driver"
	   ::= {nicTokenRingStatistics 1}
	
	nicTokenRingStatisticsEntry                          OBJECT-TYPE
		SYNTAX                                       NicTokenRingStatisticsEntry
		ACCESS                                       not-accessible
		STATUS                                       mandatory
		DESCRIPTION
			"An entry in the Token Ring statistics table"
		INDEX { nicTokenRingStatisticsIndex }
		::= {nicTokenRingStatisticsTable 1}
		
	-- name the elements in the table
	
	NicTokenRingStatisticsEntry    ::=
		SEQUENCE {
		  nicTokenRingStatisticsIndex
				INTEGER,
		  nicFunctionalAddress
				OCTET STRING,
		  nicGroupAddress
				OCTET STRING,
		  nicLastOpenStatus
				INTEGER,
		  nicRingStatus
				INTEGER,
		  nicRingState
				INTEGER
		  }
		  
	-- define each element
	
	nicTokenRingStatisticsIndex     OBJECT-TYPE
	   SYNTAX                       INTEGER
	   ACCESS                       read-only
	   STATUS                       mandatory
	   DESCRIPTION
		"Index into a list of Token Ring Statistics."
	   ::= {nicTokenRingStatisticsEntry 1}
	   
	nicFunctionalAddress            OBJECT-TYPE
	   SYNTAX                       OCTET STRING
	   ACCESS                       read-only
	   STATUS                       mandatory
	   DESCRIPTION
		"The Token Ring functional address enabled for packet reception."
	   ::= {nicTokenRingStatisticsEntry 2}
					    
	nicGroupAddress                 OBJECT-TYPE
	   SYNTAX                       OCTET STRING
	   ACCESS                       read-only
	   STATUS                       mandatory
	   DESCRIPTION
		"The Token Ring group address enabled for packet reception."
	   ::= {nicTokenRingStatisticsEntry 3}

	nicLastOpenStatus               OBJECT-TYPE
	   SYNTAX                       INTEGER
	   ACCESS                       read-only
	   STATUS                       mandatory
	   DESCRIPTION
		"The last Token Ring NdisOpenAdapter error status.  If the last open 
		 succeeded, this value will be zero."
	   ::= {nicTokenRingStatisticsEntry 4}

	nicRingStatus                   OBJECT-TYPE
	   SYNTAX                       INTEGER
	   { HardError(16384),
	     SoftError(8192),
	     TransmitBeacon(4096),
	     LobeWireFault(2048),
	     AutoRemovalError(1024),
	     RemoveReceived(512),
	     CounterOverflow(256),
	     SingleStation(128),
	     RingRecovery(64)
	     NoStatus(0)}
	   ACCESS                       read-only
	   STATUS                       mandatory
	   DESCRIPTION
		"The current Token Ring ring status."
	   ::= {nicTokenRingStatisticsEntry 5}
 
       nicRingState                     OBJECT-TYPE
	   SYNTAX                       INTEGER
	   { Opened(1),
	     Closed(2),
	     Opening(3),
	     Closing(4),
	     OpenFailure(5),
	     RingFailure(6)}   
	   ACCESS                       read-only
	   STATUS                       mandatory
	   DESCRIPTION
		"The Token Ring state of the driver with respect to entering the ring.."
	   ::= {nicTokenRingStatisticsEntry 6}

	-- the NIC Token Ring Errors Table 
	
	nicTokenRingErrorsTable                          OBJECT-TYPE
	   SYNTAX                                         SEQUENCE OF NicTokenRingErrorsEntry
	   ACCESS                                         not-accessible
	   STATUS                                         mandatory
	   DESCRIPTION
		"A list of Token Ring errors supported by the Driver"
	   ::= {nicTokenRingErrors 1}
	
	nicTokenRingErrorsEntry                              OBJECT-TYPE
		SYNTAX                                       NicTokenRingErrorsEntry
		ACCESS                                       not-accessible
		STATUS                                       mandatory
		DESCRIPTION
			"An entry in the Token Ring errors table"
		INDEX { nicTokenRingErrorsIndex }
		::= {nicTokenRingErrorsTable 1}
		
	-- name the elements in the table
	
	NicTokenRingErrorsEntry    ::=
		SEQUENCE {
		  nicTokenRingErrorsIndex
				INTEGER,
		  nicLineErrors
				INTEGER,
		  nicLostFrames
				INTEGER,
		  nicBurstErrors
				INTEGER,
		  nicACErrors
				INTEGER,
		  nicAbortDelimiters
				INTEGER,
		  nicFrameCopiedErrors
				INTEGER,
		  nicFrequencyErrors
				INTEGER,
		  nicTokenErrors
				INTEGER,
		  nicInternalErrors
				INTEGER
		  }
		  
	-- define each element
	
	nicTokenRingErrorsIndex         OBJECT-TYPE
	   SYNTAX                       INTEGER
	   ACCESS                       read-only
	   STATUS                       mandatory
	   DESCRIPTION
		"Index into a list of Token Ring Errors."
	   ::= {nicTokenRingErrorsEntry 1}
	   
	nicLineErrors                   OBJECT-TYPE
	   SYNTAX                       INTEGER
	   ACCESS                       read-only
	   STATUS                       mandatory
	   DESCRIPTION
		"The number of Token Ring frames with an invalid FCS or a code violation."
	   ::= {nicTokenRingErrorsEntry 2}
					    
	nicLostFrames                   OBJECT-TYPE
	   SYNTAX                       INTEGER
	   ACCESS                       read-only
	   STATUS                       mandatory
	   DESCRIPTION
		"The number of Token Ring frames transmitted that have not circled the
		 ring within the maximum ring latency."
	   ::= {nicTokenRingErrorsEntry 3}

	nicBurstErrors                  OBJECT-TYPE
	   SYNTAX                       INTEGER
	   ACCESS                       read-only
	   STATUS                       mandatory
	   DESCRIPTION
		"The number of Token Ring frames containing five half bits with no transition."
	   ::= {nicTokenRingErrorsEntry 4}

	nicACErrors                    OBJECT-TYPE
	   SYNTAX                       INTEGER
	   ACCESS                       read-only
	   STATUS                       mandatory
	   DESCRIPTION
		"The number of Token Ring frames with A/C errors."
	   ::= {nicTokenRingErrorsEntry 5}
 
       nicAbortDelimiters               OBJECT-TYPE
	   SYNTAX                       INTEGER
	   ACCESS                       read-only
	   STATUS                       mandatory
	   DESCRIPTION
		"The number of Token Ring abort delimiters transmitted."
	   ::= {nicTokenRingErrorsEntry 6}

       nicFrameCopiedErrors             OBJECT-TYPE
	   SYNTAX                       INTEGER
	   ACCESS                       read-only
	   STATUS                       mandatory
	   DESCRIPTION
		"The number of Token Ring frames addressed to this card that another card
		 on the ring has also copied."
	   ::= {nicTokenRingErrorsEntry 7}

       nicFrequencyErrors               OBJECT-TYPE
	   SYNTAX                       INTEGER
	   ACCESS                       read-only
	   STATUS                       mandatory
	   DESCRIPTION
		"The number of Token Ring frequency errors on the ring."
	   ::= {nicTokenRingErrorsEntry 8}

       nicTokenErrors                  OBJECT-TYPE
	   SYNTAX                       INTEGER
	   ACCESS                       read-only
	   STATUS                       mandatory
	   DESCRIPTION
		"The number of times the card has been the active Token Ring monitor
		 and has had to recreate."
	   ::= {nicTokenRingErrorsEntry 9}

       nicInternalErrors                OBJECT-TYPE
	   SYNTAX                       INTEGER
	   ACCESS                       read-only
	   STATUS                       mandatory
	   DESCRIPTION
		"The number of Token Ring internal errors the card has detected."
	   ::= {nicTokenRingErrorsEntry 10}
	
END
