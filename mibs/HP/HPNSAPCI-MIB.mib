-- ****************************************************************************
-- HP NSA PCI MIB
-- March 4, 1997
--
-- Copyright Hewlett-Packard Company 1994-1997.
-- All rights reserved.
--
-- The information in this document is subject to change without notice.
--
-- The HP enterprise number is 11. The ASN.1 prefix to, and including,
-- the HP enterprise ID is 1.3.6.1.4.1.11.
--
-- ****************************************************************************
-- Summary of objects in the HP NSA PCI Information MIB
-- ****************************************************************************
-- hp                                           (1.3.6.1.4.1.11)
--    nm                                        (hp.2)
--       hpnsa                                  (nm.23)
--          hpnsaPci Group                      (hpnsa.10)
--             hpnsaPciMibRev Group             (hpnsa.10.1)
--                hpnsaPciMibRevMajor           (hpnsa.10.1.1)
--                hpnsaPciMibRevMinor           (hpnsa.10.1.2)
--             hpnsaPciAgent Group              (hpnsa.10.2)
--                hpnsaPciAgentTable            (hpnsa.10.2.1)
--                   hpnsaPciAgentEntry         (hpnsa.10.2.1.1)
--                      hpnsaPciAgentIndex      (hpnsa.10.2.1.1.1)
--                      hpnsaPciAgentName       (hpnsa.10.2.1.1.2)
--                      hpnsaPciAgentVersion    (hpnsa.10.2.1.1.3)
--                      hpnsaPciAgentDate       (hpnsa.10.2.1.1.4)
--             hpnsaPciBios Group               (hpnsa.10.3)
--                hpnsaPciBiosPresent           (hpnsa.10.3.1)
--                hpnsaPciBiosVersion           (hpnsa.10.3.2)
--                hpnsaPciBuses                 (hpnsa.10.3.3)
--             hpnsaPciConfig Group             (hpnsa.10.4)
--                hpnsaPciTable                 (hpnsa.10.4.1)
--                   hpnsaPciEntry              (hpnsa.10.4.1.1)
--                      hpnsaPciBusIndex        (hpnsa.10.4.1.1.1)
--                      hpnsaPciDeviceIndex     (hpnsa.10.4.1.1.2)
--                      hpnsaPciFunctionIndex   (hpnsa.10.4.1.1.3)
--                      hpnsaPciVendorId        (hpnsa.10.4.1.1.4)
--                      hpnsaPciDeviceId        (hpnsa.10.4.1.1.5)
--                      hpnsaPciRevisionId      (hpnsa.10.4.1.1.6)
--                      hpnsaPciHeaderType      (hpnsa.10.4.1.1.7)
--                      hpnsaPciClassCode       (hpnsa.10.4.1.1.8)
--                      hpnsaPciCommand         (hpnsa.10.4.1.1.9)
--                      hpnsaPciStatus          (hpnsa.10.4.1.1.10)
--                      hpnsaPciCacheLineSize   (hpnsa.10.4.1.1.11)
--                      hpnsaPciLatencyTimer    (hpnsa.10.4.1.1.12)
--                      hpnsaPciBist            (hpnsa.10.4.1.1.13)
--                      hpnsaPciInterruptLine   (hpnsa.10.4.1.1.14)
--                      hpnsaPciInterruptPin    (hpnsa.10.4.1.1.15)
--                      hpnsaPciMaxLat          (hpnsa.10.4.1.1.16)
--                      hpnsaPciMinGnt          (hpnsa.10.4.1.1.17)
--                      hpnsaPciBaseAddrRegs    (hpnsa.10.4.1.1.18)
--                      hpnsaPciExpRomBaseAddr  (hpnsa.10.4.1.1.19)
--                      hpnsaPciDeviceSpecific  (hpnsa.10.4.1.1.20)
--
-- The PCI group provides a set of tables that detail the
-- configuration information regarding the PCI configuration.
--
-- Implementation of the hpnsaPci group is optional.
-- The hpnsaPci group should be included on any system with an PCI
-- bus architecture.
--
-- ****************************************************************************

HPNSAPCI-MIB DEFINITIONS ::= BEGIN
   IMPORTS
      enterprises    FROM RFC1155-SMI
      DisplayString  FROM RFC1213-MIB
      OBJECT-TYPE    FROM RFC-1212;

   hp                  OBJECT IDENTIFIER ::= { enterprises 11 }
   nm                  OBJECT IDENTIFIER ::= { hp 2 }
   hpnsa               OBJECT IDENTIFIER ::= { nm 23 }
   hpnsaPci            OBJECT IDENTIFIER ::= { hpnsa 10 }
   hpnsaPciMibRev      OBJECT IDENTIFIER ::= { hpnsaPci 1 }
   hpnsaPciAgent       OBJECT IDENTIFIER ::= { hpnsaPci 2 }
   hpnsaPciBios        OBJECT IDENTIFIER ::= { hpnsaPci 3 }
   hpnsaPciConfig      OBJECT IDENTIFIER ::= { hpnsaPci 4 }

-- ****************************************************************************
-- HP NSA PCI Information MIB Revision
-- ===================================
--
-- hp                                           (1.3.6.1.4.1.11)
--    nm                                        (hp.2)
--       hpnsa                                  (nm.23)
--          hpnsaPci Group                      (hpnsa.10)
--             hpnsaPciMibRev Group             (hpnsa.10.1)
--                hpnsaPciMibRevMajor           (hpnsa.10.1.1)
--                hpnsaPciMibRevMinor           (hpnsa.10.1.2)
--
-- Implementation of the MibRev group is mandatory for all HPNSA Agents
-- supporting the HP PCI System Information MIB.
--
-- An HPNSA Agent conforming to this document will return a
-- hpnsaPciMibRevMajor of 1 and a hpnsaPciMibRevMinor of 0.
--
-- ****************************************************************************

   hpnsaPciMibRevMajor OBJECT-TYPE
      SYNTAX INTEGER (1..65535)
      ACCESS read-only
      STATUS mandatory
      DESCRIPTION
	 "The major revision level of the MIB."
   ::= { hpnsaPciMibRev 1 }

   hpnsaPciMibRevMinor OBJECT-TYPE
      SYNTAX INTEGER (0..65535)
      ACCESS read-only
      STATUS mandatory
      DESCRIPTION
	 "The minor revision level of the MIB."
   ::= { hpnsaPciMibRev 2 }

-- ****************************************************************************
-- HP NSA PCI Info MIB Agent Information
-- =====================================
--
-- hp                                           (1.3.6.1.4.1.11)
--    nm                                        (hp.2)
--       hpnsa                                  (nm.23)
--          hpnsaPci Group                      (hpnsa.10)
--             hpnsaPciAgent Group              (hpnsa.10.2)
--                hpnsaPciAgentTable            (hpnsa.10.2.1)
--                   hpnsaPciAgentEntry         (hpnsa.10.2.1.1)
--                      hpnsaPciAgentIndex      (hpnsa.10.2.1.1.1)
--                      hpnsaPciAgentName       (hpnsa.10.2.1.1.2)
--                      hpnsaPciAgentVersion    (hpnsa.10.2.1.1.3)
--                      hpnsaPciAgentDate       (hpnsa.10.2.1.1.4)
--
-- Implementation of the PCI Agent group is mandatory for all HPNSA Agents
-- supporting the HP PCI Information MIB.
--
-- ****************************************************************************

   hpnsaPciAgentTable OBJECT-TYPE
      SYNTAX SEQUENCE OF HPnsaPciAgentEntry
      ACCESS not-accessible
      STATUS mandatory
      DESCRIPTION
	 "A table of SNMP agents that satisfy requests for this MIB."
   ::= { hpnsaPciAgent 1 }

   hpnsaPciAgentEntry OBJECT-TYPE
      SYNTAX HPnsaPciAgentEntry
      ACCESS not-accessible
      STATUS mandatory
      DESCRIPTION
	 "A description of the agent/agents that access PCI information."
      INDEX { hpnsaPciAgentIndex }
   ::= { hpnsaPciAgentTable 1 }

   HPnsaPciAgentEntry ::= SEQUENCE {
      hpnsaPciAgentIndex       INTEGER,
      hpnsaPciAgentName        DisplayString,
      hpnsaPciAgentVersion     DisplayString,
      hpnsaPciAgentDate        OCTET STRING
   }

   hpnsaPciAgentIndex OBJECT-TYPE
      SYNTAX INTEGER (0..255)
      ACCESS read-only
      STATUS mandatory
      DESCRIPTION
	 "A unique index for this agent."
   ::= { hpnsaPciAgentEntry 1 }

   hpnsaPciAgentName OBJECT-TYPE
      SYNTAX DisplayString (SIZE (0..255))
      ACCESS read-only
      STATUS mandatory
      DESCRIPTION
	 "Name of the agent/agents satisfying SNMP requests for this MIB."
   ::= { hpnsaPciAgentEntry 2 }

   hpnsaPciAgentVersion OBJECT-TYPE
      SYNTAX DisplayString (SIZE (0..10))
      ACCESS read-only
      STATUS mandatory
      DESCRIPTION
	 "Version number of the agent/agents satisfying SNMP requests for
	 this MIB."
   ::= { hpnsaPciAgentEntry 3 }

   hpnsaPciAgentDate OBJECT-TYPE
      SYNTAX OCTET STRING (SIZE (7))
      ACCESS read-only
      STATUS mandatory
      DESCRIPTION
	 "The date on which this agent was created.

	 field  octets  contents                  range
	 _________________________________________________
	    1       1    years since 1900          0..255
	    2       2    month                     1..12
	    3       3    day                       1..31
	    4       4    hour                      0..23
	    5       5    minute                    0..59
	    6       6    second                    0..59"
   ::= { hpnsaPciAgentEntry 4 }

-- ****************************************************************************
-- HP NSA PCI BIOS MIB Information
-- ===============================
--
-- hp                                           (1.3.6.1.4.1.11)
--    nm                                        (hp.2)
--       hpnsa                                  (nm.23)
--          hpnsaPci Group                      (hpnsa.10)
--             hpnsaPciBios Group               (hpnsa.10.3)
--                hpnsaPciBiosPresent           (hpnsa.10.3.1)
--                hpnsaPciBiosVersion           (hpnsa.10.3.2)
--                hpnsaPciBuses                 (hpnsa.10.3.3)
--
-- ****************************************************************************

   hpnsaPciBiosPresent OBJECT-TYPE
      SYNTAX INTEGER {
	 notPresent(0),
	 present(1)
      }
      ACCESS read-only
      STATUS mandatory
      DESCRIPTION
	 "Identifies whether PCI BIOS is present.
	 0 = not present, 1 = PCI BIOS present."
   ::= { hpnsaPciBios 1 }

   hpnsaPciBiosVersion OBJECT-TYPE
      SYNTAX INTEGER
      ACCESS read-only
      STATUS mandatory
      DESCRIPTION
	 "The PCI BIOS version number:
	 low byte = minor version, high byte = major version."
   ::= { hpnsaPciBios 2 }

   hpnsaPciBuses OBJECT-TYPE
      SYNTAX INTEGER (0..255)
      ACCESS read-only
      STATUS mandatory
      DESCRIPTION
	 "Number of PCI buses in the system"
   ::= { hpnsaPciBios 3 }

-- ****************************************************************************
-- HP NSA PCI Configuration Table
-- ==============================
--
-- hp                                           (1.3.6.1.4.1.11)
--    nm                                        (hp.2)
--       hpnsa                                  (nm.23)
--          hpnsaPci Group                      (hpnsa.10)
--             hpnsaPciConfig Group             (hpnsa.10.4)
--                hpnsaPciTable                 (hpnsa.10.4.1)
--                   hpnsaPciEntry              (hpnsa.10.4.1.1)
--                      hpnsaPciBusIndex        (hpnsa.10.4.1.1.1)
--                      hpnsaPciDeviceIndex     (hpnsa.10.4.1.1.2)
--                      hpnsaPciFunctionIndex   (hpnsa.10.4.1.1.3)
--                      hpnsaPciVendorId        (hpnsa.10.4.1.1.4)
--                      hpnsaPciDeviceId        (hpnsa.10.4.1.1.5)
--                      hpnsaPciRevisionId      (hpnsa.10.4.1.1.6)
--                      hpnsaPciHeaderType      (hpnsa.10.4.1.1.7)
--                      hpnsaPciClassCode       (hpnsa.10.4.1.1.8)
--                      hpnsaPciCommand         (hpnsa.10.4.1.1.9)
--                      hpnsaPciStatus          (hpnsa.10.4.1.1.10)
--                      hpnsaPciCacheLineSize   (hpnsa.10.4.1.1.11)
--                      hpnsaPciLatencyTimer    (hpnsa.10.4.1.1.12)
--                      hpnsaPciBist            (hpnsa.10.4.1.1.13)
--                      hpnsaPciInterruptLine   (hpnsa.10.4.1.1.14)
--                      hpnsaPciInterruptPin    (hpnsa.10.4.1.1.15)
--                      hpnsaPciMaxLat          (hpnsa.10.4.1.1.16)
--                      hpnsaPciMinGnt          (hpnsa.10.4.1.1.17)
--                      hpnsaPciBaseAddrRegs    (hpnsa.10.4.1.1.18)
--                      hpnsaPciExpRomBaseAddr  (hpnsa.10.4.1.1.19)
--                      hpnsaPciDeviceSpecific  (hpnsa.10.4.1.1.20)
--
-- Implementation of the PCI Config Table is mandatory for all
-- HPNSA Agents supporting the HP PCI information MIB.
--
-- ****************************************************************************

   hpnsaPciTable OBJECT-TYPE
      SYNTAX SEQUENCE OF HpnsaPciEntry
      ACCESS not-accessible
      STATUS mandatory
      DESCRIPTION
	 "A list of PCI device/functions entries."
   ::= { hpnsaPciConfig 1 }

   hpnsaPciEntry OBJECT-TYPE
      SYNTAX HpnsaPciEntry
      ACCESS not-accessible
      STATUS mandatory
      DESCRIPTION
	 "A description of an PCI device/function."
      INDEX { hpnsaPciBusIndex, hpnsaPciDeviceIndex,
	 hpnsaPciFunctionIndex }
   ::= { hpnsaPciTable 1 }

   HpnsaPciEntry ::= SEQUENCE {
      hpnsaPciBusIndex              INTEGER (0..255),        -- mandatory
      hpnsaPciDeviceIndex           INTEGER (0..31),         -- mandatory
      hpnsaPciFunctionIndex         INTEGER (0..7),          -- mandatory
      hpnsaPciVendorId              INTEGER,                 -- mandatory
      hpnsaPciDeviceId              INTEGER,                 -- mandatory
      hpnsaPciRevisionId            INTEGER,                 -- mandatory
      hpnsaPciHeaderType            INTEGER (0..255),        -- mandatory
      hpnsaPciClassCode             OCTET STRING (SIZE (3)), -- mandatory
      hpnsaPciCommand               INTEGER,                 -- r/w?
      hpnsaPciStatus                INTEGER,                 -- r/w to reset?
      hpnsaPciCacheLineSize         INTEGER (0..255),        -- r/w?
      hpnsaPciLatencyTimer          INTEGER (0..255),
      hpnsaPciBist                  INTEGER (0..255),        -- r/w?
      hpnsaPciInterruptLine         INTEGER (0..255),
      hpnsaPciInterruptPin          INTEGER (0..255),
      hpnsaPciMaxLat                INTEGER (0..255),
      hpnsaPciMinGnt                INTEGER (0..255),
      hpnsaPciBaseAddrRegs          OCTET STRING (SIZE (24)),
      hpnsaPciExpRomBaseAddr        OCTET STRING (SIZE (4)),
      hpnsaPciDeviceSpecific        OCTET STRING (SIZE (192))
    }

   hpnsaPciBusIndex OBJECT-TYPE
      SYNTAX INTEGER (0..255)
      ACCESS read-only
      STATUS mandatory
      DESCRIPTION
	 "The PCI Bus number that this entry describes."
   ::= { hpnsaPciEntry 1 }

   hpnsaPciDeviceIndex OBJECT-TYPE
      SYNTAX INTEGER (0..31)
      ACCESS read-only
      STATUS mandatory
      DESCRIPTION
	 "The PCI device or slot number that this entry describes."
   ::= { hpnsaPciEntry 2 }

   hpnsaPciFunctionIndex OBJECT-TYPE
      SYNTAX INTEGER (0..7)
      ACCESS read-only
      STATUS mandatory
      DESCRIPTION
	 "The PCI function that this entry describes."
   ::= { hpnsaPciEntry 3 }

   hpnsaPciVendorId OBJECT-TYPE
      SYNTAX INTEGER {
	ATI_Technologies_Inc                       (4098)
	Ulsi_Systems                               (4099),
	VLSI_Technology_Inc                        (4100),
	Avance_Logics_Inc                          (4101),
	Reply_Group                                (4102),
	Netframe_Systems_Inc                       (4103),
	Epson                                      (4104),
	Phoenix_Technologies                       (4106),
	National_Semiconductor                     (4107),
	Tseng_Labs_Inc                             (4108),
	AST_Research_Inc                           (4109),
	Weitek                                     (4110),
	Video_Logic_Ltd                            (4112),
	DEC                                        (4113),
	Micronics_Computers_Inc                    (4114),
	Cirrus_Logic                               (4115),
	IBM                                        (4116),
	ICL_Personal_Systems                       (4118),
	Spea_Software_Ag                           (4119),
	Unisys_Systems                             (4120),
	Elitegroup_Computer_Sys                    (4121),
	NCR                                        (4122),
	Vitesse_Semiconductor                      (4123),
	Western_Digital                            (4124),
	American_Megatrends                        (4126),
	Picture_Tel                                (4127),
	Hitachi_Computer_Products                  (4128),
	Oki_Electric_Industry                      (4129),
	Advanced_Micro_Devices                     (4130),
	Trident_Microsystems                       (4131),
	Zenith_Data_Systems                        (4132),
	Acer_Incorporated                          (4133),
	Dell_Computer_Corporation                  (4136),
	Siemens_Nixdorf_IS/AG                      (4137),
	Matrox                                     (4139),
	Chips_And_Technologies                     (4140),
	Wyse_Technology                            (4141),
	Olivetti_Advanced_Technology               (4142),
	Toshiba_America_Elect.                     (4143),
	TMC_Research                               (4144),
	Miro_Computer_Products_AG                  (4145),
	Compaq                                     (4146),
	NEC_Corporation                            (4147),
	Burndy_Corporation                         (4148),
	Comp.&_Comm._Resh._Lab                     (4149),
	Future_Domain                              (4150),
	Hitachi_Micro_Systems                      (4151),
	AMP,_Inc                                   (4152),
	Silicon_Integrated_System                  (4153),
	Seiko_Epson_Corporation                    (4154),
	Tatung_Co._Of_America                      (4155),
	Hewlett-Packard                            (4156),
	Solliday_Engineering                       (4158),
	Logic_Modeling                             (4159),
	Kubota_Pacific_Computer_Inc.               (4160),
	Computrend                                 (4161),
	PC_Technology_Inc                          (4162),
	Asustek_Computer,_Inc.                     (4163),
	Distributed_Processing_Technology          (4164),
	OPTI                                       (4165),
	IPC_Corporation,_Ltd.                      (4166),
	Genoa_Systems_Corp                         (4167),
	Elsa_Gmbh                                  (4168),
	Fountain_Technology                        (4169),
	Sgs_Thomson_Microelectric                  (4170),
	Buslogic                                   (4171),
	Texas_Instruments                          (4172),
	Sony_Corporation                           (4173),
	Oak_Technology,_Inc                        (4174),
	Co-Time_Computer_Ltd                       (4175),
	Winbond_Electronics_Corp                   (4176),
	Anigma,_Inc.                               (4177),
	Young_Micro_Systems                        (4178),
	Hitachi,_Ltd                               (4180),
	Efar_Microsystems                          (4181),
	ICL                                        (4182),
	Motorola_Computer                          (4183),
	Electronics_&_Telec._Rsh                   (4184),
	Teknor_Microsystems                        (4185),
	Promise_Technology                         (4186),
	Foxconn_International                      (4187),
	Wipro_Infotech_Limited                     (4188),
	Number_9_Computer_Company                  (4189),
	VTECH_Computers_Limites.                   (4190),
	Infotronic_America_Inc                     (4191),
	United_Microelectronics                    (4192),
	I.T.T.                                     (4193),
	Maspar_Computer_Corp                       (4194),
	Ocean_Office_Automation                    (4195),
	Alcatel_CIT                                (4196),
	Texas_Microsystems                         (4197),
	Picopower_Technology                       (4198),
	Mitsubishi_Electronics                     (4199),
	Diversified_Technology                     (4200),
	Mylex_Corporation                          (4201),
	Aten_Research_Inc                          (4202),
	Apple_Computer_Inc.                        (4203),
	Madge_Networks                             (4203),
	Hyundai_Electronics_Ameri                  (4204),
	Sequent                                    (4205),
	DFI,_Inc                                   (4206),
	City_Gate_Development_Ltd                  (4207),
	Daewoo_Telecom_Ltd                         (4208),
	Mitac                                      (4209),
	GIT_CO_LTD                                 (4210),
	Yamaha_Corporation                         (4211),
	Nexgen_Microsysteme                        (4212),
	Advanced_Integration_Res.                  (4213),
	Chaintech_Computer_Co_Ltd                  (4214),
	Q_Logic                                    (4215),
	Cyrix_Corporation                          (4216),
	I-BUS                                      (4217),
	Networth                                   (4218),
	Gateway_2000                               (4219),
	Goldstar_Co.,_Ltd                          (4220),
	Leadtek_Research_Inc.                      (4221),
	Interphase_Corporation                     (4222),
	Data_Technology_Corporation                (4223),
	Contaq_Microsystems_Inc.                   (4224),
	Supermac_Technology_Inc                    (4225),
	EFA_Corporation_Of_America                 (4226),
	Forex_Computer_Corporation                 (4227),
	Parador                                    (4228),
	Tulip_Computers_Int.B.V.                   (4229),
	J._Bond_Computer_Systems                   (4230),
	Cache_Computer                             (4231),
	Microcomputer_Systems__M_SON               (4232),
	Data_General_Corporation                   (4233),
	Bit3_Computer                              (4234),
	Oakleigh_Systems_Inc.                      (4236),
	Olicom                                     (4237),
	Systemsoft_Corporation                     (4239),
	Encore_Computer_Corporation                (4240),
	Intergraph_Corporation                     (4241),
	Diamond_Computer_Systems                   (4242),
	National_Instruments                       (4243),
	First_Int'l_Computers                      (4244),
	Cmd_Technology_Inc                         (4245),
	Alacron                                    (4246),
	Appian_Technology_Inc.                     (4247),
	Quantum_Designs_H.K._Ltd                   (4248),
	Samsung_Electronics_Co.,_Ltd               (4249),
	Packard_Bell                               (4250),
	Gemlight_Computer_Ltd.                     (4251),
	Megachips_Corporation                      (4252),
	Zida_Technologies_Ltd.                     (4253),
	Brooktree_Corporation                      (4254),
	Trigem_Computer_Inc.                       (4255),
	Meidensha_Corporation                      (4256),
	Juko_Electronics_Ind._Co._Ltd              (4257),
	Quantum_Corporation                        (4258),
	Everex_Systems_Inc                         (4259),
	Globe_Manufacturing_Sales                  (4260),
	Racal_Interlan                             (4261),
	Informtech_Industrial_Ltd.                 (4262),
	Benchmarq_Microelectronics                 (4263),
	Sierra_Semiconductor                       (4264),
	Silicon_Graphics                           (4265),
	Acc_Microelectronics_Corp.                 (4266),
	Digicom                                    (4267),
	Honeywell_Iasd                             (4268),
	Symphony_Labs                              (4269),
	Cornerstone_Technology                     (4270),
	Micro_Computer_Sysytems_Inc                (4271),
	Cardexpert_Technology                      (4272),
	Cabletron_Systems_Inc                      (4273),
	Raytheon_Company                           (4274),
	Databook_Inc                               (4275),
	Stb_Systems_Inc                            (4276),
	Plx_Technology                             (4277),
	3COM_Corporation                           (4279),
	Standard_Microsystems_Corporation          (4280),
	Acer_Labs                                  (4281),
	Mitsubishi_Electronics_Corp.               (4282),
	Dapha_Electronics_Corporation              (4283),
	Advanced_Logic_Research_Inc                (4284),
	Surecom_Technology                         (4285),
	Tsenglabs_International_Co.                (4286),
	Most_Inc                                   (4287),
	Boca_Research_Inc.                         (4288),
	ICM_Co.,_Ltd.                              (4289),
	Auspex_Systems_Inc.                        (4290),
	Samsung_Semiconductors                     (4291),
	Award_Software_Int'L_Inc.                  (4292),
	Xerox_Corporation                          (4293),
	Rambus_Inc.                                (4294),
	Media_Vision                               (4295),
	Neomagic_Corporation                       (4296),
	Dataexpert_Corporation                     (4297),
	Fujitsu                                    (4298),
	Omron_Corporation                          (4299),
	Mentor_Arc_Inc                             (4300),
	Advanced_System_Products                   (4301),
	Radius_Inc.                                (4302),
	Citicorp_TTI                               (4303),
	Fujitsu_Limited                            (4304),
	Future+_Systems                            (4305),
	Molex_Incorporated                         (4306),
	Jabil_Circuit_Inc                          (4307),
	Hualon_Microelectronics                    (4308),
	Autologic_Inc.                             (4309),
	Cetia                                      (4310),
	Advanced_Peripherals_Labs                  (4312),
	Macronix_International_Co.,_Ltd.           (4313),
	Thomas-Conrad_Corporation                  (4314),
	Rohm_Research                              (4315),
	Cern/Ecp/Edu                               (4316),
	Evans_&_Sutherland                         (4317),
	Nvidia_Corporation                         (4318),
	Emulex_Corporation                         (4319),
	Integrated_Micro_Solutions_Inc.            (4320),
	Tekram_Technology_Co.,Ltd.                 (4321),
	Aptix_Corporation                          (4322),
	Newbridge_Microsystems                     (4323),
	Tandem_Computers                           (4324),
	Micro_Industries_Corporation               (4325),
	Gainbery_Computer_Products_Inc.            (4326),
	Vadem                                      (4327),
	Applied_Micro_Circuits_Corporation         (4328),
	Alps_Electric_Co._Ltd.                     (4329),
	Integraphics_Systems                       (4330),
	Artists_Graphics                           (4331),
	Realtek_Semiconductor_Co.,_Ltd.            (4332),
	Ascii_Corporation                          (4333),
	Xilinx_Corporation                         (4334),
	Racore_Computer_Products,_Inc.             (4335),
	Peritek_Corporation                        (4336),
	Tyan_Computer                              (4337),
	Achme_Computer_Inc.                        (4338),
	Alaris,_Inc.                               (4339),
	S-MOS_Systems                              (4340),
	NKK_Corporation                            (4341),
	Creative_Electronic_Systems_SA             (4342),
	Matsushita_Electric_Industrial_Co.,_Ltd.   (4343),
	Altos_India_Ltd                            (4344),
	PC_Direct                                  (4345),
	Truevision                                 (4346),
	Thesys_Ges._F._Mikroelektronik_MGH         (4347),
	I-O_Data_Device,_Inc.                      (4348),
	Soyo_Technology_Co.,_Ltd.                  (4349),
	Fast_Electronic_GMBH                       (4350),
	Ncube                                      (4351),
	Jazz_Multimedia                            (4352),
	Initio_Corporation                         (4353),
	Creative_Labs                              (4354),
	Triones_Technologies,_Inc.                 (4355),
	Rasterops                                  (4356),
	Sigma_Designs,_Inc                         (4357),
	Via_Technologies,_Inc.                     (4358),
	Stratus_Computer                           (4359),
	Proteon,_Inc.                              (4360),
	Cogent_Data_Technologies                   (4361),
	Xenon_Microsystems                         (4363),
	Mini-Max_Technology,_Inc.                  (4364),
	Znyx_Advanced_Systems                      (4365),
	CPU_Technology                             (4366),
	Ross_Technology                            (4367),
	Powerhouse_Systems                         (4368),
	Santa_Cruz_Operation                       (4369),
	Rockwell_Network_Systems                   (4370),
	Accton_Technology_Corporation              (4371),
	Atmel_Corp                                 (4372),
	3dLabs                                     (4373),
	Data_Translation                           (4374),
	Datacube,_Inc                              (4375),
	Berg_Electronics                           (4376),
	Vortex_Computersysteme_Gmbh                (4377),
	Efficent_Networks,_Inc.                    (4378),
	Teledyne_Electronic_Systems                (4379),
	Tricord_Systems,_Inc.                      (4380),
	Integrated_Device_Tech                     (4381),
	Eldec_Corporaton                           (4382),
	Prescision_Digital_Images                  (4383),
	EMC_Corporation                            (4384),
	Zilog                                      (4385),
	Multi-Tech_Systems,_Inc.                   (4386),
	Leutron_Vision_Ag                          (4388),
	Eurocore                                   (4389),
	Vigra                                      (4389),
	Firmworks                                  (4393),
	Hermes_Electronics_Co.,_Ltd.               (4394),
	Linotype_-_Hell_AG                         (4395),
	Ravicad                                    (4397),
	Infomedia_Microelectronics_Inc.            (4398),
	Imaging_Technology_Inc                     (4399),
	Computervision                             (4400),
	Philips_Semiconductors                     (4401),
	Mitel_Corp                                 (4402),
	Eicon_Technology_Corporation               (4403),
	Mercury_Computer_Systems_Inc               (4404),
	Fuji_Xerox_Co_Ltd                          (4405),
	Momentum_Data_Systems                      (4406),
	Cisco_Systems_Inc                          (4407),
	Ziatech_Corporation                        (4408),
	Dynamic_Pictures_Inc                       (4409),
	FWB_Inc                                    (4410),
	Cyclone_Micro                              (4412),
	Leading_Edge_Products_Inc                  (4413),
	Sanyo_Electric_Co                          (4414),
	Equinox_Systems                            (4415),
	Intervoice_Inc                             (4416),
	Crest_Microsystem_Inc                      (4417),
	Alliance_Semiconductor_Corporation         (4418),
	Netpower,_Inc                              (4419),
	Cincinnati_Milacron                        (4420),
	Workbit_Corp                               (4421),
	Force_Computers                            (4422),
	Interface_Corp                             (4423),
	Schneider_&_Koch__Co                       (4424),
	Win_System_Corporation                     (4425),
	VMIC                                       (4426),
	Canopus_Co.,_Ltd                           (4427),
	Annabooks                                  (4428),
	IC_Corporation                             (4429),
	Nikon_Systems_Inc                          (4430),
	Digi_International                         (4431),
	Thinking_Machines_Corp                     (4432),
	Jae_Electronics_Inc.                       (4433),
	Megatek                                    (4434),
	Land_Win_Electronic_Corp                   (4435),
	Melco_Inc                                  (4436),
	Pine_Technology_Ltd                        (4437),
	Periscope_Engineering                      (4438),
	S3_Inc.                                    (21299),
	Netpower                                   (22272)
      }
      ACCESS read-only
      STATUS mandatory
      DESCRIPTION
	 "Identifies the manufacturer of the device. 0xFFFF is an
	 invalid value for a vendor ID.

		Vendor ID       Manufacturer
		---------       ------------
		  XXXX          Hewlett-Packard Co."
   ::= { hpnsaPciEntry 4 }

   hpnsaPciDeviceId OBJECT-TYPE
      SYNTAX INTEGER
      ACCESS read-only
      STATUS mandatory
      DESCRIPTION
	 "Identifies the particular device. This identier is allocated
	 by the vendor.

		Device ID       Description
		---------       ------------
		  XXXX          Blah! Blah!"
	::= { hpnsaPciEntry 5 }

   hpnsaPciRevisionId OBJECT-TYPE
      SYNTAX INTEGER
      ACCESS read-only
      STATUS mandatory
      DESCRIPTION
	 "Specifies a device specific revision identifier."
   ::= { hpnsaPciEntry 6 }

   hpnsaPciHeaderType OBJECT-TYPE
      SYNTAX INTEGER (0..255)
      ACCESS read-only
      STATUS mandatory
      DESCRIPTION
	 "Idendifies the layout of bytes 10h-3Fh in configuration
	 space and whether or not the device contains multiple
	 functions.

	 Bit 7:    1=multi-function device, 0=single function
	 Bit 6-0:  Defines layout, 0 is only layout defined,
		   all other values are reserved."
   ::= { hpnsaPciEntry 7 }

   hpnsaPciClassCode OBJECT-TYPE
      SYNTAX OCTET STRING (SIZE (3))      
      ACCESS read-only
      STATUS mandatory
      DESCRIPTION
	 "Identifies the generic function of the device.

	Base    Sub-    Prog
	Class   Class   If.    Meaning
	-----   -----   -----  -------
	 00h                   Device built before Class Code
				  definitions were finalized.
		 00h     00h   All currently implemented devices
				  except VGA compatible devices.
		 01h     00h   VGA compatible device

	 01h                   Mass Storage controller
		 00h     00h      SCSI bus controller
		 01h     00h      IDE controller
		 02h     00h      Floppy disk controller
		 03h     00h      IPI bus controller
		 80h     00h      Other mass storage controller

	 02h                   Network controller
		 00h    00h       Ethernet controller
		 01h    00h       Token Ring controller
		 02h    00h       FDDI controller
		 80h    00h       Other network controller

	 03h                   Display controller
		 00h    00h       VGA compatible controller
		 01h    00h       XGA controller
		 80h    00h       Other display controller

	 04h                   Multimedia device
		 00h    00h       Video
		 01h    00h       Audio
		 80h    00h       Other multimedia device

	 05h                   Memory controller
		 00h    00h       RAM
		 01h    00h       Flash
		 80h    00h       Other memory controller

	 06h                   Bridge device
		 00h    00h       Host bridge
		 01h    00h       ISA bridge
		 02h    00h       EISA bridge
		 03h    00h       MC bridge
		 04h    00h       PCI-to-PCI bridge
		 05h    00h       PCMCIA bridge
		 80h    00h       Other bridge device

	 07h-FEh               Reserved
	 FFh                   Device does not fit in any
				 defined classes."
   ::= { hpnsaPciEntry 8 }

   hpnsaPciCommand OBJECT-TYPE
      SYNTAX INTEGER
      ACCESS read-only
      STATUS mandatory
      DESCRIPTION
	 "Provides course control over a device's ability to generate
	 and respond to PCI cylces.

	 Bit     Description
	 ---     ------------
	  0      IO Space
	  1      Memory Space
	  2      Bus Master
	  3      Special Cycles
	  4      Memory Write and Invlaidate Enable
	  5      VGA Palette snoop
	  6      Parity Error Response
	  7      Wait cycle control
	  8      SERR# enable
	  9      Fast Back-to-Back Enable
	10-15    Reserved"

   ::= { hpnsaPciEntry 9 }

   hpnsaPciStatus OBJECT-TYPE
      SYNTAX INTEGER
      ACCESS read-only
      STATUS mandatory
      DESCRIPTION
	 "Status information for PCI bus related events.

	 Bit     Description
	 ---     ------------
	 0-6     Reserved
	  7      Fast Back-to-Back Capable
	  8      Data Parity Detected
	 9-10    DEVSEL timing; 00=fast, 01=medium, 10=slow
	 11      Signal Target Abort
	 12      Received Target Abort
	 13      Received Master Abort
	 14      Signaled System Error
	 15      Detected Parity Error"
   ::= { hpnsaPciEntry 10 }

   hpnsaPciCacheLineSize OBJECT-TYPE
      SYNTAX INTEGER (0..255)
      ACCESS read-only
      STATUS mandatory
      DESCRIPTION
	 "Specifies the system cache line size in units of 32-bit words."
   ::= { hpnsaPciEntry 11 }

   hpnsaPciLatencyTimer OBJECT-TYPE
      SYNTAX INTEGER (0..255)
      ACCESS read-only
      STATUS mandatory
      DESCRIPTION
	 "Specifies, in units of PCI bus clocks, the value of the
	 Latency Timer for this PCI bus master."
      ::= { hpnsaPciEntry 12 }

   hpnsaPciBist OBJECT-TYPE
      SYNTAX INTEGER (0..255)
      ACCESS read-only
      STATUS mandatory
      DESCRIPTION
	 "This optional register is used for control and status
	 of Built-in Self Test. Devices that don't support BIST
	 must always return a value of 0.

	 Bit     Description
	 ---     ------------
	  7      0=BIST not supported, 1=BIST supported
	  6      Wrtie a 1 to invoke BIST. Devices resets the
		 bit when BIST is complet. Software should fail
		 device if BIST is not complete after 2 seconds.
	 5-4     Reserved
	 3-0     0=Device passed test, non-zero= device-specific
		 failure code."
   ::= { hpnsaPciEntry 13 }

   hpnsaPciInterruptLine OBJECT-TYPE
      SYNTAX INTEGER (0..255)
      ACCESS read-only
      STATUS mandatory
      DESCRIPTION
	 "Communicates interrupt line routing information. The value
	 in this register tells which input of the system interrupt
	 contoller(s) the device's interrupt pin is connected to."
   ::= { hpnsaPciEntry 14 }

   hpnsaPciInterruptPin OBJECT-TYPE
      SYNTAX INTEGER (0..255)
      ACCESS read-only
      STATUS mandatory
      DESCRIPTION
	 "Tells which interrupt pin the device uses."
   ::= { hpnsaPciEntry 15 }

   hpnsaPciMaxLat OBJECT-TYPE
      SYNTAX INTEGER (0..255)
      ACCESS read-only
      STATUS mandatory
      DESCRIPTION
	 "Specifies how often the device needs to gain access to
	 the PCI bus."
   ::= { hpnsaPciEntry 16 }

   hpnsaPciMinGnt OBJECT-TYPE
      SYNTAX INTEGER (0..255)
      ACCESS read-only
      STATUS mandatory
      DESCRIPTION
	 "Specifies how long a burst period the device needs assuming
	 a clock rate of 33MHz."
   ::= { hpnsaPciEntry 17 }

   hpnsaPciBaseAddrRegs OBJECT-TYPE
      SYNTAX OCTET STRING (SIZE (24))
      ACCESS read-only
      STATUS mandatory
      DESCRIPTION
	 "Base address mapping registers for memory and IO. Refer
	 to the PCI specification for the format."
   ::= { hpnsaPciEntry 18 }

   hpnsaPciExpRomBaseAddr OBJECT-TYPE
      SYNTAX OCTET STRING (SIZE (4))
      ACCESS read-only
      STATUS mandatory
      DESCRIPTION
	 "4-byte register is defined to handle the base address
	 and size information for an expansion ROM.

	 Bit     Description
	 ---     ------------
	31-11    Expansion ROM Base Address (upper 21 bits)
	10-1     Reserved
	  0      0 = address decoding is disabled and no access
		     to this space are allowed.
		 1 = address decoding enabled."
   ::= { hpnsaPciEntry 19 }

   hpnsaPciDeviceSpecific OBJECT-TYPE
      SYNTAX OCTET STRING (SIZE (192))
      ACCESS read-only
      STATUS mandatory
      DESCRIPTION
	 "Device specific configuration space."
   ::= { hpnsaPciEntry 20 }

END
